FME workspace INPUT_BEW_CRABWSdownload.fmw
Title: INPUT_BEW_CRABWSdownload
Description: Deze workspace download data via de CRAB web service. 
    Als output wordt weggeschreven:
    - een lijst van alle RR StraatCodes met bijhorende StraatId en Straatnaam voor een bepaalde gemeente. 
    - een punten dataset met adressen met bijhorende CAPAKEY (sleutel kadastrale percelen)
Usage: PARAMETERS:
    [DestDataset]: Locatie output data. 
    [GewestId]: Kies het betrokken gewest uit de keuzelijst. 
    [Gemeente]: Geef de gewenste gemeentenaam (meerdere namen scheiden door puntkomma). 
    [Straatnaam] (optioneel): Beperk de resultaten op basis van een specifieke straatnaam. 
    [StatusStraatnaam] (optioneel): Beperk de resultaten op basis van de status van de Straatnaam. 
    [RR_StraatCode] (optioneel): Beperk de resultaten op basis van een RijksRegister StraatCode. 
    [Max_features_Straten] (optioneel): Beperk het aantal straten. (Geschikt voor testen van workspace)
    [AardWegobject] (optioneel): Beperk de resultaten op basis van de Aard Wegobject. 
    [StatusHuisnummer] (optioneel): Beperk de resultaten op basis van de status van het Huisnummer. 
    [StatusSubadres] (optioneel): Beperk de resultaten op basis van de status van het Subadres. 
    [Max_features_Huisnummers] (optioneel): Beperk het aantal Huisnummers. (Geschikt voor testen van workspace)
History: 2016-09-13,Jonas Verstraete,Initial version,2016-10-21,Jonas Verstraete,Update output format

Parameters:
- StatusSubadres =
- Max_features_Huisnummers =   # Max features to read - Huisnummers
- GewestId = 2   # Brussels Hoofdstedelijk Gewest,1%Vlaams Gewest,2%Waals Gewest,3 Gewest
- Gemeente = Gent   # Gemeente(n) (gescheiden door puntkomma)
- Straatnaam =   # Straatna(a)m(en) (gescheiden door puntkomma)
- StatusStraatnaam = 3
- RR_StraatCode =   # RR_StraatCode (gescheiden door puntkomma)
- Max_features_Straten = 5   # Max features to read - Straten
- MIN_X =
- MIN_Y =
- MAX_X =
- MAX_Y =
- AardWegobject =
- StatusHuisnummer =
- DestDataset_2 = ..\data\input   # Destination Folder
- _ws_targeturl = http://crab.agiv.be/wscrab/WsCrab.svc   # TargetUrl CRABws
- TaalCode = nl   # Taal

Writers:
- SHAPE_1: SHAPE to $(DestDataset_2)
- CSV_1: CSV to $(DestDataset_2)

Creator
    GEOMTYPE = Geometry Object
    NUM = 1
    CREATED -> CRABwsCaller
Note: INPUT_BEW_CRABWSdownload.fmw / Deze workspace download data via de CRAB web service. / Als output wordt weggeschreven: / - een lijst van alle RR StraatCodes met bijhorende StraatId en Straatnaam voor een bepaalde gemeente. / - een punten dataset met adressen met bijhorende CAPAKEY (sleutel kadastrale percelen) / PARAMETERS: / [DestDataset]: Locatie output data. / [GewestId]: Kies het betrokken gewest uit de keuzelijst. / [Gemeente]: Geef de gewenste gemeentenaam (meerdere namen scheiden door puntkomma). / [Straatnaam] (optioneel): Beperk de resultaten op basis van een specifieke straatnaam. / [StatusStraatnaam] (optioneel): Beperk de resultaten op basis van de status van de Straatnaam. / [RR_StraatCode] (optioneel): Beperk de resultaten op basis van een RijksRegister StraatCode. / [Max_features_Straten] (optioneel): Beperk het aantal straten. (Geschikt voor testen van workspace) / [AardWegobject] (optioneel): Beperk de resultaten op basis van de Aard Wegobject. / [StatusHuisnummer] (optioneel): Beperk de resultaten op basis van de status van het Huisnummer. / [StatusSubadres] (optioneel): Beperk de resultaten op basis van de status van het Subadres. / [Max_features_Huisnummers] (optioneel): Beperk het aantal Huisnummers. (Geschikt voor testen van workspace)
Note: WS-CRAB / WS-CRAB ontsluit informatie van een subset van de entiteiten uit het CRAB. Onderstaande figuur geeft een overzicht van de entiteiten en hun onderlinge samenhang. De vermelding X,Y rechtsboven in een entiteit duidt op het feit dat dit object van eenvoudige geometrische attributen (zoals een centroïde en omhullende rechthoek) is voorzien. De entiteiten aangeduid met een * beschikken over een volledige geometrische component / WS-CRAB biedt drie soorten operaties: / List XXX: oplijsten van entiteiten op basis van nul of één parameter; oplijsten van domeinwaardes; / Find XXX: zoeken van entiteiten op basis van één of meer parameters die jokertekens mogen bevatten; / Get XXX: opvragen van details van een enkele entiteit / https://www.agiv.be/producten/crab/meer-info-over-crab/gebruik-van-het-crab/crab-raadpleegdiensten/ws-crab / https://www.agiv.be/~/media/agiv/producten/crab/documenten/handleiding%20ws-crab.pdf
Note: gewest xy
CRABwsCaller
    _ws_targeturl = http://crab.agiv.be/wscrab/WsCrab.svc
    _ws_elementstomatch = GewestItem
    _ws_soapbody:
      <soapenv:Envelope xmlns:soapenv="http://schemas.xmlsoap.org/soap/envelope/" xmlns:crab="http://ws.agiv.be/crabws">
         <soapenv:Header/>
         <soapenv:Body>
            <crab:ListGewesten>
               <!--Optional:-->
               <crab:SorteerVeld>2</crab:SorteerVeld>
            </crab:ListGewesten>
         </soapenv:Body>
      </soapenv:Envelope>
    _ws_contenttype = text/xml;charset=UTF-8
    _ws_soapaction = http://ws.agiv.be/crabws/ListGewesten
    -> AttributeExposer
AttributeExposer
    ATTR_LIST = GewestId,TaalCodeGewestNaam,GewestNaam
    -> ParameterFetcher
ParameterFetcher
    ATTR_LIST = _parameter_GewestId {$(GewestId)}
    -> TestFilter
TestFilter
    DEFAULT_VALUE = <UNFILTERED>
    TEST_LIST:
      BOOL_OP,AND,COMPOSITE_TEST,<Unused>,TEST_CLAUSE,"TEST @Value(_parameter_GewestId) MATCHES_REGEX .*(\s|^)@Value(GewestId)(\s|$).*
      TEST @Value(TaalCodeGewestNaam) = $(TaalCode)",Gewest,BOOL_OP,AND,COMPOSITE_TEST,<Unused>,TEST_CLAUSE,"TEST _parameter_GewestId ATTRIBUTE_IS_EMPTY """"
      TEST @Value(TaalCodeGewestNaam) = $(TaalCode)",no param
    Gewest -> BulkAttributeRemover_2
    no param -> BulkAttributeRemover_2
    <UNFILTERED> -> TestFilter__Unfiltered_
BulkAttributeRemover_2
    ATTR_EXP = ^_parameter_|^_element_
    -> CRABwsCaller_2
    -> Gewesten [off]
Note: rijksregister straat
Gewesten: Inspector
Note: gemeente xy
CRABwsCaller_2
    _ws_targeturl = http://crab.agiv.be/wscrab/WsCrab.svc
    _ws_elementstomatch = GemeenteItem
    _ws_soapbody:
      <soapenv:Envelope xmlns:soapenv="http://schemas.xmlsoap.org/soap/envelope/" xmlns:crab="http://ws.agiv.be/crabws">
         <soapenv:Header/>
         <soapenv:Body>
            <crab:ListGemeentenByGewestId>
               <crab:GewestId>@Value(GewestId)</crab:GewestId>
               <!--Optional:-->
               <crab:SorteerVeld>2</crab:SorteerVeld>
            </crab:ListGemeentenByGewestId>
         </soapenv:Body>
      </soapenv:Envelope>
    _ws_contenttype = text/xml;charset=UTF-8
    _ws_soapaction = http://ws.agiv.be/crabws/ListGemeentenByGewestId
    -> AttributeExposer_2
AttributeExposer_2
    ATTR_LIST = GemeenteId,GemeenteNaam,TaalCodeGemeenteNaam,TaalCode,NISGemeenteCode
    -> ParameterFetcher_2
ParameterFetcher_2
    ATTR_LIST = _parameter_Gemeente {$(Gemeente)}
    -> TestFilter_3
TestFilter_3
    DEFAULT_VALUE = <UNFILTERED>
    TEST_LIST:
      BOOL_OP,AND,COMPOSITE_TEST,<Unused>,TEST_CLAUSE,"TEST @Value(_parameter_Gemeente) MATCHES_REGEX .*(;|^)@Value(GemeenteNaam)(;|$).*
      TEST @Value(TaalCodeGemeenteNaam) = $(TaalCode)",Gemeente,BOOL_OP,AND,COMPOSITE_TEST,<Unused>,TEST_CLAUSE,"TEST _parameter_Gemeente ATTRIBUTE_IS_EMPTY """"
      TEST @Value(TaalCodeGemeenteNaam) = $(TaalCode)",no param
    Gemeente -> BulkAttributeRemover_3
    no param -> BulkAttributeRemover_3
    <UNFILTERED> -> TestFilter__Unfiltered__2
BulkAttributeRemover_3
    ATTR_EXP = ^_parameter_|^_element_
    -> CRABwsCaller_3
    -> Gemeenten [off]
Gemeenten: Inspector
Note: straatnaam [met status]
CRABwsCaller_3
    _ws_targeturl = http://crab.agiv.be/wscrab/WsCrab.svc
    _ws_elementstomatch = StraatnaamWithStatusItem
    _ws_soapbody:
      <soapenv:Envelope xmlns:soapenv="http://schemas.xmlsoap.org/soap/envelope/" xmlns:crab="http://ws.agiv.be/crabws">
         <soapenv:Header/>
         <soapenv:Body>
            <crab:ListStraatnamenWithStatusByGemeenteId>
               <crab:GemeenteId>@Value(GemeenteId)</crab:GemeenteId>
               <!--Optional:-->
               <crab:SorteerVeld>2</crab:SorteerVeld>
            </crab:ListStraatnamenWithStatusByGemeenteId>
         </soapenv:Body>
      </soapenv:Envelope>
    _ws_contenttype = text/xml;charset=UTF-8
    _ws_soapaction = http://ws.agiv.be/crabws/ListStraatnamenWithStatusByGemeenteId
    -> AttributeExposer_3
AttributeExposer_3
    ATTR_LIST = StraatnaamId,Straatnaam,TaalCode,StraatnaamLabel,StatusStraatnaam
    -> ParameterFetcher_3
ParameterFetcher_3
    ATTR_LIST = _parameter_Straatnaam {$(Straatnaam)}
    -> TestFilter_4
TestFilter_4
    DEFAULT_VALUE = <UNFILTERED>
    TEST_LIST:
      BOOL_OP,COMPOSITE,COMPOSITE_TEST,"""(1 OR 2) AND 3""",TEST_CLAUSE,"TEST @Value(_parameter_Straatnaam) MATCHES_REGEX .*(;|^)@Value(Straatnaam)(;|$).*
      TEST @Value(_parameter_Straatnaam) MATCHES_REGEX .*(;|^)@Value(StraatnaamLabel)(;|$).*
      TEST @Value(TaalCode) = $(TaalCode)",Straat,BOOL_OP,AND,COMPOSITE_TEST,<Unused>,TEST_CLAUSE,"TEST _parameter_Straatnaam ATTRIBUTE_IS_EMPTY """"
      TEST @Value(TaalCode) = $(TaalCode)",no param
    Straat -> BulkAttributeRemover_4
    no param -> BulkAttributeRemover_4
BulkAttributeRemover_4
    ATTR_EXP = ^_parameter_|^_element_
    -> BulkAttributeRemover_3_Output_2
    -> TestFilter_6
BulkAttributeRemover_3_Output_2: Inspector
TestFilter_6
    DEFAULT_VALUE = <UNFILTERED>
    TEST_LIST = BOOL_OP,OR,COMPOSITE_TEST,<Unused>,TEST_CLAUSE,"TEST $(Max_features_Straten) > 0",NOT_ATTRIBUTE_IS_EMPTY
    NOT_ATTRIBUTE_IS_EMPTY -> Counter
    <UNFILTERED> -> PassThrough
Counter
    START = 1
    DOMAIN = counter
    SCOPE = Local
    CNT_ATTR = _count
    -> TestFilter_7
TestFilter_7
    DEFAULT_VALUE = <UNFILTERED>
    TEST_LIST = BOOL_OP,OR,COMPOSITE_TEST,<Unused>,TEST_CLAUSE,"TEST @Value(_count) <= $(Max_features_Straten)",@Value(_count) <= $(Max_features_Straten)
    @Value(_count) <= $(Max_features_Straten) -> AttributeRemover
AttributeRemover
    REMOVE_ATTRS = _count
    -> PassThrough
PassThrough: Tester
    TEST_MODE = Automatic
    TEST_CLAUSE = TEST 0 = 0
    TEST_DESCRIPTION = ""
    BOOL_OP = OR
    PASSED -> FeatureMerger [REQUESTOR]
TestFilter__Unfiltered__2: Inspector
TestFilter__Unfiltered_: Inspector
Creator_2
    GEOMTYPE = Geometry Object
    NUM = 1
    CREATED -> CRABwsCaller_4
CRABwsCaller_4
    _ws_targeturl = http://crab.agiv.be/wscrab/WsCrab.svc
    _ws_elementstomatch = CodeItem
    _ws_soapbody:
      <soapenv:Envelope xmlns:soapenv="http://schemas.xmlsoap.org/soap/envelope/" xmlns:crab="http://ws.agiv.be/crabws">
         <soapenv:Header/>
         <soapenv:Body>
            <crab:ListStatusStraatnamen>
               <!--Optional:-->
               <crab:SorteerVeld>1</crab:SorteerVeld>
            </crab:ListStatusStraatnamen>
         </soapenv:Body>
      </soapenv:Envelope>
    _ws_contenttype = text/xml;charset=UTF-8
    _ws_soapaction = http://ws.agiv.be/crabws/ListStatusStraatnamen
    -> AttributeExposer_4
AttributeExposer_4
    ATTR_LIST = Code,Naam,Definitie
    -> BulkAttributeRenamer
BulkAttributeRenamer
    PATTERN_ACTION_DISP = Add String Prefix
    ATTRLIST = Code Definitie Naam
    REPLACE_STR = StatusStraatnaam_
    ATTRCHOICE = Selected Attributes
    -> BulkAttributeRenamer_7
BulkAttributeRenamer_7
    CASE_DISP = yes
    PATTERN_ACTION_DISP = Remove Suffix String
    ATTRLIST = StatusStraatnaam_Code
    REPLACE_STR = _Code
    ATTRCHOICE = Selected Attributes
    -> FeatureMerger [SUPPLIER]
FeatureMerger
    PROCESS_DUPS = No
    ATTR_CONFLICT_RES = Use Requestor
    ATTR_ACCUM_MODE = Merge Supplier
    SUPPLIERS_FIRST = No
    JOIN_KEYS = @Value(StatusStraatnaam) @Value(StatusStraatnaam) AUTO
    IGNORE_NULLS = No
    MERGE_TYPE = Attributes Only
    MERGED -> ParameterFetcher_4
    NOT_MERGED -> FeatureMerger_NotMerged
ParameterFetcher_4
    ATTR_LIST = _parameter_StatusStraatnaam {$(StatusStraatnaam)}
    -> TestFilter_2
TestFilter_2
    DEFAULT_VALUE = <UNFILTERED>
    TEST_LIST = BOOL_OP,OR,COMPOSITE_TEST,<Unused>,TEST_CLAUSE,"TEST @Value(_parameter_StatusStraatnaam) MATCHES_REGEX .*(\s|^)@Value(StatusStraatnaam)(\s|$).*",StatusStraatnaam,BOOL_OP,AND,COMPOSITE_TEST,<Unused>,TEST_CLAUSE,"TEST _parameter_StatusStraatnaam ATTRIBUTE_IS_EMPTY """"",no param
    StatusStraatnaam -> BulkAttributeRemover_5
    no param -> BulkAttributeRemover_5
BulkAttributeRemover_5
    ATTR_EXP = ^_parameter_|^_element_
    -> CRABwsCaller_5
    -> Straatnamen_status [off]
    -> CRABwsCaller_6
    -> CRABwsCaller_14
RR_Straatnamen: Inspector
AttributeRenamer
    ATTR_LIST = RR_StraatCode,StraatCode,,RR_SubkantonCode,SubkantonCode,,StraatnaamId,StraatId,,NISGemeenteCode,NISGemeenteCode,,GemeenteNaam,Gemeente,
    -> AttributeRenamer_3
AttributeRenamer_3
    ATTR_TABLE:
      RENAME_SET_DEFAULT SubkantonC > SubkantonCode
      RENAME_SET_DEFAULT NISGemeent > NISGemeenteCode
    -> CRAB_RijksregisterStraat (writer CSV_1)
CRAB_RijksregisterStraat (writer CSV_1)
    attributes: StraatCode char(4), StraatId char(5), Straatnaam char(100), SubkantonCode char(4), NISGemeenteCode char(5), Gemeente char(50)
Straatnamen_status: Inspector
FeatureMerger_NotMerged: Inspector
Creator_10
    GEOMTYPE = Geometry Object
    NUM = 1
    CREATED -> CRABwsCaller_18
CRABwsCaller_18
    _ws_targeturl = http://crab.agiv.be/wscrab/WsCrab.svc
    _ws_elementstomatch = CodeItem
    _ws_soapbody:
      <soapenv:Envelope xmlns:soapenv="http://schemas.xmlsoap.org/soap/envelope/" xmlns:crab="http://ws.agiv.be/crabws">
         <soapenv:Header/>
         <soapenv:Body>
            <crab:ListStatusHuisnummers>
               <!--Optional:-->
               <crab:SorteerVeld>1</crab:SorteerVeld>
            </crab:ListStatusHuisnummers>
         </soapenv:Body>
      </soapenv:Envelope>
    _ws_contenttype = text/xml;charset=UTF-8
    _ws_soapaction = http://ws.agiv.be/crabws/ListStatusHuisnummers
    -> AttributeExposer_18
AttributeExposer_18
    ATTR_LIST = Code,Naam,Definitie
    -> BulkAttributeRenamer_21
BulkAttributeRenamer_21
    PATTERN_ACTION_DISP = Add String Prefix
    ATTRLIST = Code Definitie Naam
    REPLACE_STR = StatusHuisnummer_
    ATTRCHOICE = Selected Attributes
    -> BulkAttributeRenamer_22
BulkAttributeRenamer_22
    CASE_DISP = yes
    PATTERN_ACTION_DISP = Remove Suffix String
    ATTRLIST = StatusHuisnummer_Code
    REPLACE_STR = _Code
    ATTRCHOICE = Selected Attributes
    -> FeatureMerger_9 [SUPPLIER]
Creator_13
    GEOMTYPE = Geometry Object
    NUM = 1
    CREATED -> CRABwsCaller_23
CRABwsCaller_23
    _ws_targeturl = http://crab.agiv.be/wscrab/WsCrab.svc
    _ws_elementstomatch = CodeItem
    _ws_soapbody:
      <soapenv:Envelope xmlns:soapenv="http://schemas.xmlsoap.org/soap/envelope/" xmlns:crab="http://ws.agiv.be/crabws">
         <soapenv:Header/>
         <soapenv:Body>
            <crab:ListStatusSubadressen>
               <!--Optional:-->
               <crab:SorteerVeld>1</crab:SorteerVeld>
            </crab:ListStatusSubadressen>
         </soapenv:Body>
      </soapenv:Envelope>
    _ws_contenttype = text/xml;charset=UTF-8
    _ws_soapaction = http://ws.agiv.be/crabws/ListStatusSubadressen
    -> AttributeExposer_23
AttributeExposer_23
    ATTR_LIST = Code,Naam,Definitie
    -> BulkAttributeRenamer_28
BulkAttributeRenamer_28
    PATTERN_ACTION_DISP = Add String Prefix
    ATTRLIST = Code Definitie Naam
    REPLACE_STR = StatusSubadres_
    ATTRCHOICE = Selected Attributes
    -> BulkAttributeRenamer_29
BulkAttributeRenamer_29
    CASE_DISP = yes
    PATTERN_ACTION_DISP = Remove Suffix String
    ATTRLIST = StatusSubadres_Code
    REPLACE_STR = _Code
    ATTRCHOICE = Selected Attributes
    -> FeatureMerger_12 [SUPPLIER]
Creator_8
    GEOMTYPE = Geometry Object
    NUM = 1
    CREATED -> CRABwsCaller_15
Creator_9
    GEOMTYPE = Geometry Object
    NUM = 1
    CREATED -> CRABwsCaller_16
Straatnamen_extra: Inspector
Note: huisnummer [met status]
CRABwsCaller_17
    _ws_targeturl = http://crab.agiv.be/wscrab/WsCrab.svc
    _ws_elementstomatch = HuisnummerWithStatusItem
    _ws_soapbody:
      <soapenv:Envelope xmlns:soapenv="http://schemas.xmlsoap.org/soap/envelope/" xmlns:crab="http://ws.agiv.be/crabws">
         <soapenv:Header/>
         <soapenv:Body>
            <crab:ListHuisnummersWithStatusByStraatnaamId>
               <crab:StraatnaamId>@Value(StraatnaamId)</crab:StraatnaamId>
               <!--Optional:-->
               <crab:SorteerVeld>2</crab:SorteerVeld>
            </crab:ListHuisnummersWithStatusByStraatnaamId>
         </soapenv:Body>
      </soapenv:Envelope>
    _ws_contenttype = text/xml;charset=UTF-8
    _ws_soapaction = http://ws.agiv.be/crabws/ListHuisnummersWithStatusByStraatnaamId
    -> AttributeExposer_17
AttributeExposer_17
    ATTR_LIST = HuisnummerId,Huisnummer,StatusHuisnummer
    -> BulkAttributeRemover_18
BulkAttributeRemover_18
    ATTR_EXP = ^_parameter_|^_element_
    -> FeatureMerger_9 [REQUESTOR]
FeatureMerger_9
    PROCESS_DUPS = No
    ATTR_CONFLICT_RES = Use Requestor
    ATTR_ACCUM_MODE = Merge Supplier
    SUPPLIERS_FIRST = No
    JOIN_KEYS = @Value(StatusHuisnummer) @Value(StatusHuisnummer) AUTO
    IGNORE_NULLS = No
    MERGE_TYPE = Attributes Only
    MERGED -> ParameterFetcher_14
    NOT_MERGED -> FeatureMerger_NotMerged_9
ParameterFetcher_14
    ATTR_LIST = _parameter_StatusHuisnummer {$(StatusHuisnummer)}
    -> TestFilter_17
TestFilter_17
    DEFAULT_VALUE = <UNFILTERED>
    TEST_LIST = BOOL_OP,OR,COMPOSITE_TEST,<Unused>,TEST_CLAUSE,"TEST @Value(_parameter_StatusHuisnummer) MATCHES_REGEX .*(\s|^)@Value(StatusHuisnummer)(\s|$).*",StatusHuisnummer,BOOL_OP,AND,COMPOSITE_TEST,<Unused>,TEST_CLAUSE,"TEST _parameter_StatusHuisnummer ATTRIBUTE_IS_EMPTY """"",no param
    StatusHuisnummer -> BulkAttributeRemover_19
    no param -> BulkAttributeRemover_19
BulkAttributeRemover_19
    ATTR_EXP = ^_parameter_|^_element_
    -> Huisnummers [off]
    -> TestFilter_24
    -> FeatureMerger_16 [REQUESTOR]
Huisnummers: Inspector
TestFilter_24
    DEFAULT_VALUE = <UNFILTERED>
    TEST_LIST = BOOL_OP,OR,COMPOSITE_TEST,<Unused>,TEST_CLAUSE,"TEST $(Max_features_Huisnummers) > 0",NOT_ATTRIBUTE_IS_EMPTY
    NOT_ATTRIBUTE_IS_EMPTY -> Counter_2
    <UNFILTERED> -> PassThrough_2
Counter_2
    START = 1
    DOMAIN = counter
    SCOPE = Local
    CNT_ATTR = _count
    -> TestFilter_25
TestFilter_25
    DEFAULT_VALUE = <UNFILTERED>
    TEST_LIST = BOOL_OP,OR,COMPOSITE_TEST,<Unused>,TEST_CLAUSE,"TEST @Value(_count) <= $(Max_features_Huisnummers)",@Value(_count) <= $(Max_features_Huisnummers)
    @Value(_count) <= $(Max_features_Huisnummers) -> AttributeRemover_2
AttributeRemover_2
    REMOVE_ATTRS = _count
    -> PassThrough_2
PassThrough_2: Tester
    TEST_MODE = Automatic
    TEST_CLAUSE = TEST 0 = 0
    TEST_DESCRIPTION = ""
    BOOL_OP = OR
    PASSED -> CRABwsCaller_19
FeatureMerger_NotMerged_9: Inspector
Creator_11
    GEOMTYPE = Geometry Object
    NUM = 1
    CREATED -> CRABwsCaller_20
Creator_12
    GEOMTYPE = Geometry Object
    NUM = 1
    CREATED -> CRABwsCaller_21
Huisnummers_extra: Inspector
Note: subadres [met status]
CRABwsCaller_22
    _ws_targeturl = http://crab.agiv.be/wscrab/WsCrab.svc
    _ws_elementstomatch = SubadresWithStatusItem
    _ws_soapbody:
      <soapenv:Envelope xmlns:soapenv="http://schemas.xmlsoap.org/soap/envelope/" xmlns:crab="http://ws.agiv.be/crabws">
         <soapenv:Header/>
         <soapenv:Body>
            <crab:ListSubadressenWithStatusByHuisnummerId>
               <crab:HuisnummerId>@Value(HuisnummerId)</crab:HuisnummerId>
               <!--Optional:-->
               <crab:SorteerVeld>2</crab:SorteerVeld>
            </crab:ListSubadressenWithStatusByHuisnummerId>
         </soapenv:Body>
      </soapenv:Envelope>
    _ws_contenttype = text/xml;charset=UTF-8
    _ws_soapaction = http://ws.agiv.be/crabws/ListSubadressenWithStatusByHuisnummerId
    -> AttributeExposer_22
AttributeExposer_22
    ATTR_LIST = SubadresId,Subadres,StatusSubadres
    -> BulkAttributeRemover_23
BulkAttributeRemover_23
    ATTR_EXP = ^_parameter_|^_element_
    -> FeatureMerger_12 [REQUESTOR]
FeatureMerger_12
    PROCESS_DUPS = No
    ATTR_CONFLICT_RES = Use Requestor
    ATTR_ACCUM_MODE = Merge Supplier
    SUPPLIERS_FIRST = No
    JOIN_KEYS = @Value(StatusSubadres) @Value(StatusSubadres) AUTO
    IGNORE_NULLS = No
    MERGE_TYPE = Attributes Only
    MERGED -> ParameterFetcher_18
    NOT_MERGED -> FeatureMerger_NotMerged_12
ParameterFetcher_18
    ATTR_LIST = _parameter_StatusSubadres {$(StatusSubadres)}
    -> TestFilter_21
TestFilter_21
    DEFAULT_VALUE = <UNFILTERED>
    TEST_LIST = BOOL_OP,OR,COMPOSITE_TEST,<Unused>,TEST_CLAUSE,"TEST @Value(_parameter_StatusSubadres) MATCHES_REGEX .*(\s|^)@Value(StatusSubadres)(\s|$).*",StatusSubadres,BOOL_OP,AND,COMPOSITE_TEST,<Unused>,TEST_CLAUSE,"TEST _parameter_StatusSubadres ATTRIBUTE_IS_EMPTY """"",no param
    StatusSubadres -> BulkAttributeRemover_24
    no param -> BulkAttributeRemover_24
BulkAttributeRemover_24
    ATTR_EXP = ^_parameter_|^_element_
    -> Subadres [off]
    -> CRABwsCaller_24
    -> FeatureMerger_16 [SUPPLIER]
FeatureMerger_16
    PROCESS_DUPS = No
    ATTR_CONFLICT_RES = Use Requestor
    ATTR_ACCUM_MODE = Merge Supplier
    SUPPLIERS_FIRST = No
    JOIN_KEYS = @Value(HuisnummerId) @Value(HuisnummerId) AUTO
    IGNORE_NULLS = No
    MERGE_TYPE = Attributes Only
    NOT_MERGED -> Huisnummers_noSubadres [off]
Huisnummers_noSubadres: Inspector
Subadres: Inspector
FeatureMerger_NotMerged_12: Inspector
Note: perceel xy
CRABwsCaller_27
    _ws_targeturl = http://crab.agiv.be/wscrab/WsCrab.svc
    _ws_elementstomatch = PerceelItem
    _ws_soapbody:
      <soapenv:Envelope xmlns:soapenv="http://schemas.xmlsoap.org/soap/envelope/" xmlns:crab="http://ws.agiv.be/crabws">
         <soapenv:Header/>
         <soapenv:Body>
            <crab:ListPercelenByHuisnummerId>
               <crab:HuisnummerId>@Value(HuisnummerId)</crab:HuisnummerId>
            </crab:ListPercelenByHuisnummerId>
         </soapenv:Body>
      </soapenv:Envelope>
    _ws_contenttype = text/xml;charset=UTF-8
    _ws_soapaction = http://ws.agiv.be/crabws/ListPercelenByHuisnummerId
    -> AttributeExposer_27
AttributeExposer_27
    ATTR_LIST = IdentificatorPerceel
    -> BulkAttributeRemover_28
Creator_14
    GEOMTYPE = Geometry Object
    NUM = 1
    CREATED -> CRABwsCaller_25
Creator_15
    GEOMTYPE = Geometry Object
    NUM = 1
    CREATED -> CRABwsCaller_26
FeatureMerger_15
    PROCESS_DUPS = No
    ATTR_CONFLICT_RES = Use Requestor
    ATTR_ACCUM_MODE = Merge Supplier
    SUPPLIERS_FIRST = No
    JOIN_KEYS = @Value(HuisnummerId) @Value(HuisnummerId) AUTO
    IGNORE_NULLS = No
    MERGE_TYPE = Attributes Only
    NOT_MERGED -> Huisnummers_noSubadres_extra [off]
Huisnummers_noSubadres_extra: Inspector
Subadres_extra: Inspector
TestFilter_10
    DEFAULT_VALUE = SearchEnvelop
    TEST_LIST:
      BOOL_OP,OR,COMPOSITE_TEST,<Unused>,TEST_CLAUSE,"TEST $(MIN_X) NOT_> 0
      TEST $(MIN_Y) NOT_> 0
      TEST $(MAX_X) NOT_> 0
      TEST $(MAX_Y) NOT_> 0",No SearchEnvelop
Sampler
    SAMPLE_TYPE_LONG = First N Features
    RATE = 1
    SAMPLED -> AttributeCreator
    SAMPLED -> SpatialRelator [Requestor]
    NOT_SAMPLED -> SpatialRelator [Requestor]
AttributeCreator
    ATTR_LIST = _envelope_wkt,POLYGON (($(MIN_X) $(MIN_Y), $(MAX_X) $(MIN_Y), $(MAX_X) $(MAX_Y), $(MIN_X) $(MAX_Y), $(MIN_X) $(MIN_Y)))
    -> GeometryReplacer
GeometryReplacer
    KIND_LONG = OGC Well Known Text
    SOURCE = @Value(_envelope_wkt)
    REMOVE_ATTRIBUTE = Yes
    OGC_WKT_PRECISION_DISPLAY = 64-bit
    -> SpatialRelator [Supplier]
SpatialRelator
    CALC_CARD = No
    PREDICATES = INTERSECTS
    LIST_NAME = _relationships
    CURVE_BOUNDARY_RULE_PARAM = Default Rule
    SUCCESS_ATTR = _related_candidates
    -> PassThrough_3
PassThrough_3: Tester
    TEST_MODE = Automatic
    TEST_CLAUSE = TEST 0 = 0
    TEST_DESCRIPTION = ""
    BOOL_OP = OR
Creator_6
    GEOMTYPE = Geometry Object
    NUM = 1
    CREATED -> CRABwsCaller_12
Creator_7
    GEOMTYPE = Geometry Object
    NUM = 1
    CREATED -> CRABwsCaller_13
RR_Straatnamen_extra: Inspector
Note: wegobject xy
Creator_3
    GEOMTYPE = Geometry Object
    NUM = 1
    CREATED -> CRABwsCaller_7
Wegobject: Inspector
Creator_4
    GEOMTYPE = Geometry Object
    NUM = 1
    CREATED -> CRABwsCaller_9
Creator_5
    GEOMTYPE = Geometry Object
    NUM = 1
    CREATED -> CRABwsCaller_10
WegObject_extra: Inspector
Creator_17
    GEOMTYPE = Geometry Object
    NUM = 1
    CREATED -> CRABwsCaller_30
Creator_18
    GEOMTYPE = Geometry Object
    NUM = 1
    CREATED -> CRABwsCaller_31
ParameterFetcher_21
    ATTR_LIST = _parameter_Straatnaam {$(Straatnaam)}
    -> TestFilter_26
TestFilter_26
    DEFAULT_VALUE = <UNFILTERED>
    TEST_LIST:
      BOOL_OP,COMPOSITE,COMPOSITE_TEST,"""(1 OR 2) AND 3""",TEST_CLAUSE,"TEST @Value(_parameter_Straatnaam) MATCHES_REGEX .*(;|^)@Value(Straatnaam)(;|$).*
      TEST @Value(_parameter_Straatnaam) MATCHES_REGEX .*(;|^)@Value(StraatnaamLabel)(;|$).*
      TEST @Value(TaalCode) = $(TaalCode)",Straat,BOOL_OP,AND,COMPOSITE_TEST,<Unused>,TEST_CLAUSE,"TEST _parameter_Straatnaam ATTRIBUTE_IS_EMPTY """"
      TEST @Value(TaalCode) = $(TaalCode)",no param
    Straat -> BulkAttributeRemover_28
    no param -> BulkAttributeRemover_28
BulkAttributeRemover_28
    ATTR_EXP = ^_parameter_|^_element_
    -> CRABwsCaller_29
VertexCreator
    XVAL = @Value(CenterX)
    INDEX = 0
    YVAL = @Value(CenterY)
    MODE_NAME = Add Point
    -> Percelen [off]
    -> AttributeRenamer_2
Percelen: Inspector
AttributeRenamer_2
    ATTR_LIST = CenterX,CenterX,,CenterY,CenterY,,NISGemeenteCode,NISCode,,GemeenteNaam,Gemeente,,GewestNaam,Gewest,,Huisnummer,Huisnr,,IdentificatorPerceel,capakey,,StatusHuisnummer_Naam,hsnrstatus,,Straatnaam,Straat,
    -> CRAB_Percelen_CenterPoints (writer SHAPE_1)
CRAB_Percelen_CenterPoints (writer SHAPE_1)
    attributes: Gewest char(40), NISCode char(10), Gemeente char(40), Straat char(50), Huisnr char(5), hsnrstatus char(40), capakey char(32), CenterX number(20,10), CenterY number(20,10)

Bookmark: Straten Rijksregister
CRABwsCaller_5
    _ws_targeturl = http://crab.agiv.be/wscrab/WsCrab.svc
    _ws_elementstomatch = RijksregisterstraatItem
    _ws_soapbody:
      <soapenv:Envelope xmlns:soapenv="http://schemas.xmlsoap.org/soap/envelope/" xmlns:crab="http://ws.agiv.be/crabws">
         <soapenv:Header/>
         <soapenv:Body>
            <crab:ListRijksregisterStratenByStraatnaamId>
               <crab:StraatnaamId>@Value(StraatnaamId)</crab:StraatnaamId>
            </crab:ListRijksregisterStratenByStraatnaamId>
         </soapenv:Body>
      </soapenv:Envelope>
    _ws_contenttype = text/xml;charset=UTF-8
    _ws_soapaction = http://ws.agiv.be/crabws/ListRijksregisterStratenByStraatnaamId
    -> AttributeExposer_5
AttributeExposer_5
    ATTR_LIST = StraatCode,SubkantonCode
    -> BulkAttributeRenamer_2
BulkAttributeRenamer_2
    PATTERN_ACTION_DISP = Add String Prefix
    ATTRLIST = StraatCode SubkantonCode
    REPLACE_STR = RR_
    ATTRCHOICE = Selected Attributes
    -> ParameterFetcher_5
ParameterFetcher_5
    ATTR_LIST = _parameter_RR_StraatCode {$(RR_StraatCode)}
    -> TestFilter_5
TestFilter_5
    DEFAULT_VALUE = <UNFILTERED>
    TEST_LIST = BOOL_OP,OR,COMPOSITE_TEST,<Unused>,TEST_CLAUSE,"TEST @Value(_parameter_RR_StraatCode) MATCHES_REGEX .*(;|^)@Value(RR_StraatCode)(;|$).*",RR_StraatCode,BOOL_OP,AND,COMPOSITE_TEST,<Unused>,TEST_CLAUSE,"TEST _parameter_RR_StraatCode ATTRIBUTE_IS_EMPTY """"",no param
    RR_StraatCode -> BulkAttributeRemover_6
    no param -> BulkAttributeRemover_6
BulkAttributeRemover_6
    ATTR_EXP = ^_parameter_|^_element_
    -> RR_Straatnamen [off]
    -> CRABwsCaller_11
    -> AttributeRenamer

Bookmark: Get RijksregisterStraatByRijksregisterStraatCode
CRABwsCaller_11
    _ws_targeturl = http://crab.agiv.be/wscrab/WsCrab.svc
    _ws_elementstomatch = GetRijksregisterStraatByRijksregisterStraatCodeResult
    _ws_soapbody:
      <soapenv:Envelope xmlns:soapenv="http://schemas.xmlsoap.org/soap/envelope/" xmlns:crab="http://ws.agiv.be/crabws">
         <soapenv:Header/>
         <soapenv:Body>
            <crab:GetRijksregisterStraatByRijksregisterStraatCode>
               <crab:StraatCode>@Value(RR_StraatCode)</crab:StraatCode>
               <crab:SubkantonCode>@Value(RR_SubkantonCode)</crab:SubkantonCode>
            </crab:GetRijksregisterStraatByRijksregisterStraatCode>
         </soapenv:Body>
      </soapenv:Envelope>
    _ws_contenttype = text/xml;charset=UTF-8
    _ws_soapaction = http://ws.agiv.be/crabws/GetRijksregisterStraatByRijksregisterStraatCode
    -> AttributeExposer_11
AttributeExposer_11
    ATTR_LIST = BeginDatum,BeginTijd,BeginBewerking,BeginOrganisatie
    -> BulkAttributeRenamer_11
BulkAttributeRenamer_11
    PATTERN_ACTION_DISP = Add String Prefix
    ATTRLIST = BeginBewerking BeginDatum BeginOrganisatie BeginTijd
    REPLACE_STR = rrstr.
    ATTRCHOICE = Selected Attributes
    -> BulkAttributeRemover_12
BulkAttributeRemover_12
    ATTR_EXP = ^_parameter_|^_element_
    -> FeatureMerger_5 [REQUESTOR]

Bookmark: Straten Wegobject
CRABwsCaller_6
    _ws_targeturl = http://crab.agiv.be/wscrab/WsCrab.svc
    _ws_elementstomatch = WegobjectItem
    _ws_soapbody:
      <soapenv:Envelope xmlns:soapenv="http://schemas.xmlsoap.org/soap/envelope/" xmlns:crab="http://ws.agiv.be/crabws">
         <soapenv:Header/>
         <soapenv:Body>
            <crab:ListWegobjectenByStraatnaamId>
               <crab:StraatnaamId>@Value(StraatnaamId)</crab:StraatnaamId>
               <!--Optional:-->
               <crab:SorteerVeld>1</crab:SorteerVeld>
            </crab:ListWegobjectenByStraatnaamId>
         </soapenv:Body>
      </soapenv:Envelope>
    _ws_contenttype = text/xml;charset=UTF-8
    _ws_soapaction = http://ws.agiv.be/crabws/ListWegobjectenByStraatnaamId
    -> AttributeExposer_6
AttributeExposer_6
    ATTR_LIST = AardWegobject,IdentificatorWegobject
    -> BulkAttributeRemover_7
BulkAttributeRemover_7
    ATTR_EXP = ^_parameter_|^_element_
    -> FeatureMerger_2 [REQUESTOR]

Bookmark: GetStraatnaamWithStatusByStraatnaamId
CRABwsCaller_14
    _ws_targeturl = http://crab.agiv.be/wscrab/WsCrab.svc
    _ws_elementstomatch = GetStraatnaamWithStatusByStraatnaamIdResult
    _ws_soapbody:
      <soapenv:Envelope xmlns:soapenv="http://schemas.xmlsoap.org/soap/envelope/" xmlns:crab="http://ws.agiv.be/crabws">
         <soapenv:Header/>
         <soapenv:Body>
            <crab:GetStraatnaamWithStatusByStraatnaamId>
               <crab:StraatnaamId>@Value(StraatnaamId)</crab:StraatnaamId>
            </crab:GetStraatnaamWithStatusByStraatnaamId>
         </soapenv:Body>
      </soapenv:Envelope>
    _ws_contenttype = text/xml;charset=UTF-8
    _ws_soapaction = http://ws.agiv.be/crabws/GetStraatnaamWithStatusByStraatnaamId
    -> AttributeExposer_14
AttributeExposer_14
    ATTR_LIST = BeginDatum,BeginTijd,BeginBewerking,BeginOrganisatie
    -> BulkAttributeRenamer_16
BulkAttributeRenamer_16
    PATTERN_ACTION_DISP = Add String Prefix
    ATTRLIST = BeginBewerking BeginDatum BeginOrganisatie BeginTijd
    REPLACE_STR = strnm.
    ATTRCHOICE = Selected Attributes
    -> BulkAttributeRemover_15
BulkAttributeRemover_15
    ATTR_EXP = ^_parameter_|^_element_
    -> FeatureMerger_7 [REQUESTOR]

Bookmark: ListBewerkingen BeginBewerking
CRABwsCaller_15
    _ws_targeturl = http://crab.agiv.be/wscrab/WsCrab.svc
    _ws_elementstomatch = CodeItem
    _ws_soapbody:
      <soapenv:Envelope xmlns:soapenv="http://schemas.xmlsoap.org/soap/envelope/" xmlns:crab="http://ws.agiv.be/crabws">
         <soapenv:Header/>
         <soapenv:Body>
            <crab:ListBewerkingen>
               <!--Optional:-->
               <crab:SorteerVeld>1</crab:SorteerVeld>
            </crab:ListBewerkingen>
         </soapenv:Body>
      </soapenv:Envelope>
    _ws_contenttype = text/xml;charset=UTF-8
    _ws_soapaction = http://ws.agiv.be/crabws/ListBewerkingen
    -> AttributeExposer_15
AttributeExposer_15
    ATTR_LIST = Code,Naam,Definitie
    -> BulkAttributeRenamer_17
BulkAttributeRenamer_17
    PATTERN_ACTION_DISP = Add String Prefix
    ATTRLIST = Code Definitie Naam
    REPLACE_STR = strnm.BeginBewerking_
    ATTRCHOICE = Selected Attributes
    -> BulkAttributeRenamer_19
BulkAttributeRenamer_19
    CASE_DISP = yes
    PATTERN_ACTION_DISP = Remove Suffix String
    ATTRLIST = strnm.BeginBewerking_Code
    REPLACE_STR = _Code
    ATTRCHOICE = Selected Attributes
    -> FeatureMerger_7 [SUPPLIER]
FeatureMerger_7
    PROCESS_DUPS = No
    ATTR_CONFLICT_RES = Use Requestor
    ATTR_ACCUM_MODE = Merge Supplier
    SUPPLIERS_FIRST = No
    JOIN_KEYS = @Value(strnm.BeginBewerking) @Value(strnm.BeginBewerking) AUTO
    IGNORE_NULLS = No
    MERGE_TYPE = Attributes Only
    MERGED -> BulkAttributeRemover_16
    NOT_MERGED -> FeatureMerger_NotMerged_7
BulkAttributeRemover_16
    ATTR_EXP = ^_parameter_|^_element_
    -> FeatureMerger_8 [REQUESTOR]
FeatureMerger_NotMerged_7: Inspector

Bookmark: ListOrganisaties BeginOrganisatie
CRABwsCaller_16
    _ws_targeturl = http://crab.agiv.be/wscrab/WsCrab.svc
    _ws_elementstomatch = CodeItem
    _ws_soapbody:
      <soapenv:Envelope xmlns:soapenv="http://schemas.xmlsoap.org/soap/envelope/" xmlns:crab="http://ws.agiv.be/crabws">
         <soapenv:Header/>
         <soapenv:Body>
            <crab:ListOrganisaties>
               <!--Optional:-->
               <crab:SorteerVeld>1</crab:SorteerVeld>
            </crab:ListOrganisaties>
         </soapenv:Body>
      </soapenv:Envelope>
    _ws_contenttype = text/xml;charset=UTF-8
    _ws_soapaction = http://ws.agiv.be/crabws/ListOrganisaties
    -> AttributeExposer_16
AttributeExposer_16
    ATTR_LIST = Code,Naam,Definitie
    -> BulkAttributeRenamer_18
BulkAttributeRenamer_18
    PATTERN_ACTION_DISP = Add String Prefix
    ATTRLIST = Code Definitie Naam
    REPLACE_STR = strnm.BeginOrganisatie_
    ATTRCHOICE = Selected Attributes
    -> BulkAttributeRenamer_20
BulkAttributeRenamer_20
    CASE_DISP = yes
    PATTERN_ACTION_DISP = Remove Suffix String
    ATTRLIST = strnm.BeginOrganisatie_Code
    REPLACE_STR = _Code
    ATTRCHOICE = Selected Attributes
    -> FeatureMerger_8 [SUPPLIER]
FeatureMerger_8
    PROCESS_DUPS = No
    ATTR_CONFLICT_RES = Use Requestor
    ATTR_ACCUM_MODE = Merge Supplier
    SUPPLIERS_FIRST = No
    JOIN_KEYS = @Value(strnm.BeginOrganisatie) @Value(strnm.BeginOrganisatie) AUTO
    IGNORE_NULLS = No
    MERGE_TYPE = Attributes Only
    MERGED -> BulkAttributeRemover_17
    NOT_MERGED -> FeatureMerger_NotMerged_8
BulkAttributeRemover_17
    ATTR_EXP = ^_parameter_|^_element_
    -> Straatnamen_extra [off]
    -> CRABwsCaller_17
FeatureMerger_NotMerged_8: Inspector

Bookmark: GetHuisnummerWithStatusByHuisnummerId
CRABwsCaller_19
    _ws_targeturl = http://crab.agiv.be/wscrab/WsCrab.svc
    _ws_elementstomatch = GetHuisnummerWithStatusByHuisnummerIdResult
    _ws_soapbody:
      <soapenv:Envelope xmlns:soapenv="http://schemas.xmlsoap.org/soap/envelope/" xmlns:crab="http://ws.agiv.be/crabws">
         <soapenv:Header/>
         <soapenv:Body>
            <crab:GetHuisnummerWithStatusByHuisnummerId>
               <crab:HuisnummerId>@Value(HuisnummerId)</crab:HuisnummerId>
            </crab:GetHuisnummerWithStatusByHuisnummerId>
         </soapenv:Body>
      </soapenv:Envelope>
    _ws_contenttype = text/xml;charset=UTF-8
    _ws_soapaction = http://ws.agiv.be/crabws/GetHuisnummerWithStatusByHuisnummerId
    -> AttributeExposer_19
AttributeExposer_19
    ATTR_LIST = BeginDatum,BeginTijd,BeginBewerking,BeginOrganisatie
    -> BulkAttributeRenamer_23
BulkAttributeRenamer_23
    PATTERN_ACTION_DISP = Add String Prefix
    ATTRLIST = BeginBewerking BeginDatum BeginOrganisatie BeginTijd
    REPLACE_STR = hsnr.
    ATTRCHOICE = Selected Attributes
    -> BulkAttributeRemover_20
BulkAttributeRemover_20
    ATTR_EXP = ^_parameter_|^_element_
    -> FeatureMerger_10 [REQUESTOR]

Bookmark: ListBewerkingen BeginBewerking
CRABwsCaller_20
    _ws_targeturl = http://crab.agiv.be/wscrab/WsCrab.svc
    _ws_elementstomatch = CodeItem
    _ws_soapbody:
      <soapenv:Envelope xmlns:soapenv="http://schemas.xmlsoap.org/soap/envelope/" xmlns:crab="http://ws.agiv.be/crabws">
         <soapenv:Header/>
         <soapenv:Body>
            <crab:ListBewerkingen>
               <!--Optional:-->
               <crab:SorteerVeld>1</crab:SorteerVeld>
            </crab:ListBewerkingen>
         </soapenv:Body>
      </soapenv:Envelope>
    _ws_contenttype = text/xml;charset=UTF-8
    _ws_soapaction = http://ws.agiv.be/crabws/ListBewerkingen
    -> AttributeExposer_20
AttributeExposer_20
    ATTR_LIST = Code,Naam,Definitie
    -> BulkAttributeRenamer_24
BulkAttributeRenamer_24
    PATTERN_ACTION_DISP = Add String Prefix
    ATTRLIST = Code Definitie Naam
    REPLACE_STR = hsnr.BeginBewerking_
    ATTRCHOICE = Selected Attributes
    -> BulkAttributeRenamer_26
BulkAttributeRenamer_26
    CASE_DISP = yes
    PATTERN_ACTION_DISP = Remove Suffix String
    ATTRLIST = hsnr.BeginBewerking_Code
    REPLACE_STR = _Code
    ATTRCHOICE = Selected Attributes
    -> FeatureMerger_10 [SUPPLIER]
FeatureMerger_10
    PROCESS_DUPS = No
    ATTR_CONFLICT_RES = Use Requestor
    ATTR_ACCUM_MODE = Merge Supplier
    SUPPLIERS_FIRST = No
    JOIN_KEYS = @Value(hsnr.BeginBewerking) @Value(hsnr.BeginBewerking) AUTO
    IGNORE_NULLS = No
    MERGE_TYPE = Attributes Only
    MERGED -> BulkAttributeRemover_21
    NOT_MERGED -> FeatureMerger_NotMerged_10
BulkAttributeRemover_21
    ATTR_EXP = ^_parameter_|^_element_
    -> FeatureMerger_11 [REQUESTOR]
FeatureMerger_NotMerged_10: Inspector

Bookmark: ListOrganisaties BeginOrganisatie
CRABwsCaller_21
    _ws_targeturl = http://crab.agiv.be/wscrab/WsCrab.svc
    _ws_elementstomatch = CodeItem
    _ws_soapbody:
      <soapenv:Envelope xmlns:soapenv="http://schemas.xmlsoap.org/soap/envelope/" xmlns:crab="http://ws.agiv.be/crabws">
         <soapenv:Header/>
         <soapenv:Body>
            <crab:ListOrganisaties>
               <!--Optional:-->
               <crab:SorteerVeld>1</crab:SorteerVeld>
            </crab:ListOrganisaties>
         </soapenv:Body>
      </soapenv:Envelope>
    _ws_contenttype = text/xml;charset=UTF-8
    _ws_soapaction = http://ws.agiv.be/crabws/ListOrganisaties
    -> AttributeExposer_21
AttributeExposer_21
    ATTR_LIST = Code,Naam,Definitie
    -> BulkAttributeRenamer_25
BulkAttributeRenamer_25
    PATTERN_ACTION_DISP = Add String Prefix
    ATTRLIST = Code Definitie Naam
    REPLACE_STR = hsnr.BeginOrganisatie_
    ATTRCHOICE = Selected Attributes
    -> BulkAttributeRenamer_27
BulkAttributeRenamer_27
    CASE_DISP = yes
    PATTERN_ACTION_DISP = Remove Suffix String
    ATTRLIST = hsnr.BeginOrganisatie_Code
    REPLACE_STR = _Code
    ATTRCHOICE = Selected Attributes
    -> FeatureMerger_11 [SUPPLIER]
FeatureMerger_11
    PROCESS_DUPS = No
    ATTR_CONFLICT_RES = Use Requestor
    ATTR_ACCUM_MODE = Merge Supplier
    SUPPLIERS_FIRST = No
    JOIN_KEYS = @Value(hsnr.BeginOrganisatie) @Value(hsnr.BeginOrganisatie) AUTO
    IGNORE_NULLS = No
    MERGE_TYPE = Attributes Only
    MERGED -> BulkAttributeRemover_22
    NOT_MERGED -> FeatureMerger_NotMerged_11
BulkAttributeRemover_22
    ATTR_EXP = ^_parameter_|^_element_
    -> Huisnummers_extra [off]
    -> CRABwsCaller_22
    -> FeatureMerger_15 [REQUESTOR]
    -> CRABwsCaller_27
FeatureMerger_NotMerged_11: Inspector

Bookmark: GetStraatnaamWithStatusByStraatnaamId
CRABwsCaller_24
    _ws_targeturl = http://crab.agiv.be/wscrab/WsCrab.svc
    _ws_elementstomatch = GetSubadresWithStatusBySubadresIdResult
    _ws_soapbody:
      <soapenv:Envelope xmlns:soapenv="http://schemas.xmlsoap.org/soap/envelope/" xmlns:crab="http://ws.agiv.be/crabws">
         <soapenv:Header/>
         <soapenv:Body>
            <crab:GetSubadresWithStatusBySubadresId>
               <crab:SubadresId>@Value(SubadresId)</crab:SubadresId>
            </crab:GetSubadresWithStatusBySubadresId>
         </soapenv:Body>
      </soapenv:Envelope>
    _ws_contenttype = text/xml;charset=UTF-8
    _ws_soapaction = http://ws.agiv.be/crabws/GetSubadresWithStatusBySubadresId
    -> AttributeExposer_24
AttributeExposer_24
    ATTR_LIST = BeginDatum,BeginTijd,BeginBewerking,BeginOrganisatie
    -> BulkAttributeRenamer_30
BulkAttributeRenamer_30
    PATTERN_ACTION_DISP = Add String Prefix
    ATTRLIST = BeginBewerking BeginDatum BeginOrganisatie BeginTijd
    REPLACE_STR = sbadr.
    ATTRCHOICE = Selected Attributes
    -> BulkAttributeRemover_25
BulkAttributeRemover_25
    ATTR_EXP = ^_parameter_|^_element_
    -> FeatureMerger_13 [REQUESTOR]

Bookmark: ListBewerkingen BeginBewerking
CRABwsCaller_25
    _ws_targeturl = http://crab.agiv.be/wscrab/WsCrab.svc
    _ws_elementstomatch = CodeItem
    _ws_soapbody:
      <soapenv:Envelope xmlns:soapenv="http://schemas.xmlsoap.org/soap/envelope/" xmlns:crab="http://ws.agiv.be/crabws">
         <soapenv:Header/>
         <soapenv:Body>
            <crab:ListBewerkingen>
               <!--Optional:-->
               <crab:SorteerVeld>1</crab:SorteerVeld>
            </crab:ListBewerkingen>
         </soapenv:Body>
      </soapenv:Envelope>
    _ws_contenttype = text/xml;charset=UTF-8
    _ws_soapaction = http://ws.agiv.be/crabws/ListBewerkingen
    -> AttributeExposer_25
AttributeExposer_25
    ATTR_LIST = Code,Naam,Definitie
    -> BulkAttributeRenamer_31
BulkAttributeRenamer_31
    PATTERN_ACTION_DISP = Add String Prefix
    ATTRLIST = Code Definitie Naam
    REPLACE_STR = sbadr.BeginBewerking_
    ATTRCHOICE = Selected Attributes
    -> BulkAttributeRenamer_33
BulkAttributeRenamer_33
    CASE_DISP = yes
    PATTERN_ACTION_DISP = Remove Suffix String
    ATTRLIST = sbadr.BeginBewerking_Code
    REPLACE_STR = _Code
    ATTRCHOICE = Selected Attributes
    -> FeatureMerger_13 [SUPPLIER]
FeatureMerger_13
    PROCESS_DUPS = No
    ATTR_CONFLICT_RES = Use Requestor
    ATTR_ACCUM_MODE = Merge Supplier
    SUPPLIERS_FIRST = No
    JOIN_KEYS = @Value(sbadr.BeginBewerking) @Value(sbadr.BeginBewerking) AUTO
    IGNORE_NULLS = No
    MERGE_TYPE = Attributes Only
    MERGED -> BulkAttributeRemover_26
    NOT_MERGED -> FeatureMerger_NotMerged_13
BulkAttributeRemover_26
    ATTR_EXP = ^_parameter_|^_element_
    -> FeatureMerger_14 [REQUESTOR]
FeatureMerger_NotMerged_13: Inspector

Bookmark: ListOrganisaties BeginOrganisatie
CRABwsCaller_26
    _ws_targeturl = http://crab.agiv.be/wscrab/WsCrab.svc
    _ws_elementstomatch = CodeItem
    _ws_soapbody:
      <soapenv:Envelope xmlns:soapenv="http://schemas.xmlsoap.org/soap/envelope/" xmlns:crab="http://ws.agiv.be/crabws">
         <soapenv:Header/>
         <soapenv:Body>
            <crab:ListOrganisaties>
               <!--Optional:-->
               <crab:SorteerVeld>1</crab:SorteerVeld>
            </crab:ListOrganisaties>
         </soapenv:Body>
      </soapenv:Envelope>
    _ws_contenttype = text/xml;charset=UTF-8
    _ws_soapaction = http://ws.agiv.be/crabws/ListOrganisaties
    -> AttributeExposer_26
AttributeExposer_26
    ATTR_LIST = Code,Naam,Definitie
    -> BulkAttributeRenamer_32
BulkAttributeRenamer_32
    PATTERN_ACTION_DISP = Add String Prefix
    ATTRLIST = Code Definitie Naam
    REPLACE_STR = sbadr.BeginOrganisatie_
    ATTRCHOICE = Selected Attributes
    -> BulkAttributeRenamer_34
BulkAttributeRenamer_34
    CASE_DISP = yes
    PATTERN_ACTION_DISP = Remove Suffix String
    ATTRLIST = sbadr.BeginOrganisatie_Code
    REPLACE_STR = _Code
    ATTRCHOICE = Selected Attributes
    -> FeatureMerger_14 [SUPPLIER]
FeatureMerger_14
    PROCESS_DUPS = No
    ATTR_CONFLICT_RES = Use Requestor
    ATTR_ACCUM_MODE = Merge Supplier
    SUPPLIERS_FIRST = No
    JOIN_KEYS = @Value(sbadr.BeginOrganisatie) @Value(sbadr.BeginOrganisatie) AUTO
    IGNORE_NULLS = No
    MERGE_TYPE = Attributes Only
    MERGED -> BulkAttributeRemover_27
    NOT_MERGED -> FeatureMerger_NotMerged_14
BulkAttributeRemover_27
    ATTR_EXP = ^_parameter_|^_element_
    -> Subadres_extra [off]
    -> FeatureMerger_15 [SUPPLIER]
FeatureMerger_NotMerged_14: Inspector

Bookmark: ListBewerkingen BeginBewerking
CRABwsCaller_12
    _ws_targeturl = http://crab.agiv.be/wscrab/WsCrab.svc
    _ws_elementstomatch = CodeItem
    _ws_soapbody:
      <soapenv:Envelope xmlns:soapenv="http://schemas.xmlsoap.org/soap/envelope/" xmlns:crab="http://ws.agiv.be/crabws">
         <soapenv:Header/>
         <soapenv:Body>
            <crab:ListBewerkingen>
               <!--Optional:-->
               <crab:SorteerVeld>1</crab:SorteerVeld>
            </crab:ListBewerkingen>
         </soapenv:Body>
      </soapenv:Envelope>
    _ws_contenttype = text/xml;charset=UTF-8
    _ws_soapaction = http://ws.agiv.be/crabws/ListBewerkingen
    -> AttributeExposer_12
AttributeExposer_12
    ATTR_LIST = Code,Naam,Definitie
    -> BulkAttributeRenamer_12
BulkAttributeRenamer_12
    PATTERN_ACTION_DISP = Add String Prefix
    ATTRLIST = Code Definitie Naam
    REPLACE_STR = rrstr.BeginBewerking_
    ATTRCHOICE = Selected Attributes
    -> BulkAttributeRenamer_14
BulkAttributeRenamer_14
    CASE_DISP = yes
    PATTERN_ACTION_DISP = Remove Suffix String
    ATTRLIST = rrstr.BeginBewerking_Code
    REPLACE_STR = _Code
    ATTRCHOICE = Selected Attributes
    -> FeatureMerger_5 [SUPPLIER]
FeatureMerger_5
    PROCESS_DUPS = No
    ATTR_CONFLICT_RES = Use Requestor
    ATTR_ACCUM_MODE = Merge Supplier
    SUPPLIERS_FIRST = No
    JOIN_KEYS = @Value(rrstr.BeginBewerking) @Value(rrstr.BeginBewerking) AUTO
    IGNORE_NULLS = No
    MERGE_TYPE = Attributes Only
    MERGED -> BulkAttributeRemover_13
    NOT_MERGED -> FeatureMerger_NotMerged_5
BulkAttributeRemover_13
    ATTR_EXP = ^_parameter_|^_element_
    -> FeatureMerger_6 [REQUESTOR]
FeatureMerger_NotMerged_5: Inspector

Bookmark: ListOrganisaties BeginOrganisatie
CRABwsCaller_13
    _ws_targeturl = http://crab.agiv.be/wscrab/WsCrab.svc
    _ws_elementstomatch = CodeItem
    _ws_soapbody:
      <soapenv:Envelope xmlns:soapenv="http://schemas.xmlsoap.org/soap/envelope/" xmlns:crab="http://ws.agiv.be/crabws">
         <soapenv:Header/>
         <soapenv:Body>
            <crab:ListOrganisaties>
               <!--Optional:-->
               <crab:SorteerVeld>1</crab:SorteerVeld>
            </crab:ListOrganisaties>
         </soapenv:Body>
      </soapenv:Envelope>
    _ws_contenttype = text/xml;charset=UTF-8
    _ws_soapaction = http://ws.agiv.be/crabws/ListOrganisaties
    -> AttributeExposer_13
AttributeExposer_13
    ATTR_LIST = Code,Naam,Definitie
    -> BulkAttributeRenamer_13
BulkAttributeRenamer_13
    PATTERN_ACTION_DISP = Add String Prefix
    ATTRLIST = Code Definitie Naam
    REPLACE_STR = rrstr.BeginOrganisatie_
    ATTRCHOICE = Selected Attributes
    -> BulkAttributeRenamer_15
BulkAttributeRenamer_15
    CASE_DISP = yes
    PATTERN_ACTION_DISP = Remove Suffix String
    ATTRLIST = rrstr.BeginOrganisatie_Code
    REPLACE_STR = _Code
    ATTRCHOICE = Selected Attributes
    -> FeatureMerger_6 [SUPPLIER]
FeatureMerger_6
    PROCESS_DUPS = No
    ATTR_CONFLICT_RES = Use Requestor
    ATTR_ACCUM_MODE = Merge Supplier
    SUPPLIERS_FIRST = No
    JOIN_KEYS = @Value(rrstr.BeginOrganisatie) @Value(rrstr.BeginOrganisatie) AUTO
    IGNORE_NULLS = No
    MERGE_TYPE = Attributes Only
    MERGED -> BulkAttributeRemover_14
    NOT_MERGED -> FeatureMerger_NotMerged_6
BulkAttributeRemover_14
    ATTR_EXP = ^_parameter_|^_element_
    -> RR_Straatnamen_extra [off]
FeatureMerger_NotMerged_6: Inspector

Bookmark: Get Aard Straten Wegobject
CRABwsCaller_7
    _ws_targeturl = http://crab.agiv.be/wscrab/WsCrab.svc
    _ws_elementstomatch = CodeItem
    _ws_soapbody:
      <soapenv:Envelope xmlns:soapenv="http://schemas.xmlsoap.org/soap/envelope/" xmlns:crab="http://ws.agiv.be/crabws">
         <soapenv:Header/>
         <soapenv:Body>
            <crab:ListAardWegobjecten>
               <!--Optional:-->
               <crab:SorteerVeld>1</crab:SorteerVeld>
            </crab:ListAardWegobjecten>
         </soapenv:Body>
      </soapenv:Envelope>
    _ws_contenttype = text/xml;charset=UTF-8
    _ws_soapaction = http://ws.agiv.be/crabws/ListAardWegobjecten
    -> AttributeExposer_7
AttributeExposer_7
    ATTR_LIST = Code,Naam,Definitie
    -> BulkAttributeRenamer_4
BulkAttributeRenamer_4
    PATTERN_ACTION_DISP = Add String Prefix
    ATTRLIST = Code Definitie Naam
    REPLACE_STR = AardWegobject_
    ATTRCHOICE = Selected Attributes
    -> BulkAttributeRenamer_8
BulkAttributeRenamer_8
    CASE_DISP = yes
    PATTERN_ACTION_DISP = Remove Suffix String
    ATTRLIST = AardWegobject_Code
    REPLACE_STR = _Code
    ATTRCHOICE = Selected Attributes
    -> FeatureMerger_2 [SUPPLIER]
FeatureMerger_2
    PROCESS_DUPS = No
    ATTR_CONFLICT_RES = Use Requestor
    ATTR_ACCUM_MODE = Merge Supplier
    SUPPLIERS_FIRST = No
    JOIN_KEYS = @Value(AardWegobject) @Value(AardWegobject) AUTO
    IGNORE_NULLS = No
    MERGE_TYPE = Attributes Only
    MERGED -> ParameterFetcher_7
    NOT_MERGED -> FeatureMerger_NotMerged_2
ParameterFetcher_7
    ATTR_LIST = _parameter_AardWegobject {$(AardWegobject)}
    -> TestFilter_12
TestFilter_12
    DEFAULT_VALUE = <UNFILTERED>
    TEST_LIST = BOOL_OP,OR,COMPOSITE_TEST,<Unused>,TEST_CLAUSE,"TEST @Value(_parameter_AardWegobject) MATCHES_REGEX .*(\s|^)@Value(AardWegobject)(\s|$).*",AardWegobject,BOOL_OP,AND,COMPOSITE_TEST,<Unused>,TEST_CLAUSE,"TEST _parameter_AardWegobject ATTRIBUTE_IS_EMPTY """"",no param
    AardWegobject -> BulkAttributeRemover_8
    no param -> BulkAttributeRemover_8
BulkAttributeRemover_8
    ATTR_EXP = ^_parameter_|^_element_
    -> CRABwsCaller_8
    -> Wegobject [off]
FeatureMerger_NotMerged_2: Inspector

Bookmark: Get Wegobject by IdentificatorWegobject
CRABwsCaller_8
    _ws_targeturl = http://crab.agiv.be/wscrab/WsCrab.svc
    _ws_elementstomatch = GetWegobjectByIdentificatorWegobjectResult
    _ws_soapbody:
      <soapenv:Envelope xmlns:soapenv="http://schemas.xmlsoap.org/soap/envelope/" xmlns:crab="http://ws.agiv.be/crabws">
         <soapenv:Header/>
         <soapenv:Body>
            <crab:GetWegobjectByIdentificatorWegobject>
               <crab:IdentificatorWegobject>@Value(IdentificatorWegobject)</crab:IdentificatorWegobject>
            </crab:GetWegobjectByIdentificatorWegobject>
         </soapenv:Body>
      </soapenv:Envelope>
    _ws_contenttype = text/xml;charset=UTF-8
    _ws_soapaction = http://ws.agiv.be/crabws/GetWegobjectByIdentificatorWegobject
    -> AttributeExposer_8
AttributeExposer_8
    ATTR_LIST = CenterX,CenterY,MinimumX,MinimumY,MaximumX,MaximumY,BeginDatum,BeginTijd,BeginBewerking,BeginOrganisatie
    -> BulkAttributeRenamer_5
BulkAttributeRenamer_5
    PATTERN_ACTION_DISP = Add String Prefix
    ATTRLIST = BeginBewerking BeginDatum BeginOrganisatie BeginTijd CenterX CenterY MaximumX MaximumY MinimumX MinimumY
    REPLACE_STR = wgobj.
    ATTRCHOICE = Selected Attributes
    -> BulkAttributeRemover_9
BulkAttributeRemover_9
    ATTR_EXP = ^_parameter_|^_element_
    -> FeatureMerger_3 [REQUESTOR]

Bookmark: ListBewerkingen BeginBewerking
CRABwsCaller_9
    _ws_targeturl = http://crab.agiv.be/wscrab/WsCrab.svc
    _ws_elementstomatch = CodeItem
    _ws_soapbody:
      <soapenv:Envelope xmlns:soapenv="http://schemas.xmlsoap.org/soap/envelope/" xmlns:crab="http://ws.agiv.be/crabws">
         <soapenv:Header/>
         <soapenv:Body>
            <crab:ListBewerkingen>
               <!--Optional:-->
               <crab:SorteerVeld>1</crab:SorteerVeld>
            </crab:ListBewerkingen>
         </soapenv:Body>
      </soapenv:Envelope>
    _ws_contenttype = text/xml;charset=UTF-8
    _ws_soapaction = http://ws.agiv.be/crabws/ListBewerkingen
    -> AttributeExposer_9
AttributeExposer_9
    ATTR_LIST = Code,Naam,Definitie
    -> BulkAttributeRenamer_3
BulkAttributeRenamer_3
    PATTERN_ACTION_DISP = Add String Prefix
    ATTRLIST = Code Definitie Naam
    REPLACE_STR = wgobj.BeginBewerking_
    ATTRCHOICE = Selected Attributes
    -> BulkAttributeRenamer_9
BulkAttributeRenamer_9
    CASE_DISP = yes
    PATTERN_ACTION_DISP = Remove Suffix String
    ATTRLIST = wgobj.BeginBewerking_Code
    REPLACE_STR = _Code
    ATTRCHOICE = Selected Attributes
    -> FeatureMerger_3 [SUPPLIER]
FeatureMerger_3
    PROCESS_DUPS = No
    ATTR_CONFLICT_RES = Use Requestor
    ATTR_ACCUM_MODE = Merge Supplier
    SUPPLIERS_FIRST = No
    JOIN_KEYS = @Value(wgobj.BeginBewerking) @Value(wgobj.BeginBewerking) AUTO
    IGNORE_NULLS = No
    MERGE_TYPE = Attributes Only
    MERGED -> ParameterFetcher_6
    NOT_MERGED -> FeatureMerger_NotMerged_3
ParameterFetcher_6
    ATTR_LIST = _parameter_AardWegobject {$(AardWegobject)}
    -> TestFilter_8
TestFilter_8
    DEFAULT_VALUE = <UNFILTERED>
    TEST_LIST = BOOL_OP,OR,COMPOSITE_TEST,<Unused>,TEST_CLAUSE,"TEST @Value(_parameter_AardWegobject) MATCHES_REGEX .*(\s|^)@Value(AardWegobject)(\s|$).*",AardWegobject,BOOL_OP,AND,COMPOSITE_TEST,<Unused>,TEST_CLAUSE,"TEST _parameter_AardWegobject ATTRIBUTE_IS_EMPTY """"",no param
    AardWegobject -> BulkAttributeRemover_10
    no param -> BulkAttributeRemover_10
BulkAttributeRemover_10
    ATTR_EXP = ^_parameter_|^_element_
    -> FeatureMerger_4 [REQUESTOR]
FeatureMerger_NotMerged_3: Inspector

Bookmark: ListOrganisaties BeginOrganisatie
CRABwsCaller_10
    _ws_targeturl = http://crab.agiv.be/wscrab/WsCrab.svc
    _ws_elementstomatch = CodeItem
    _ws_soapbody:
      <soapenv:Envelope xmlns:soapenv="http://schemas.xmlsoap.org/soap/envelope/" xmlns:crab="http://ws.agiv.be/crabws">
         <soapenv:Header/>
         <soapenv:Body>
            <crab:ListOrganisaties>
               <!--Optional:-->
               <crab:SorteerVeld>1</crab:SorteerVeld>
            </crab:ListOrganisaties>
         </soapenv:Body>
      </soapenv:Envelope>
    _ws_contenttype = text/xml;charset=UTF-8
    _ws_soapaction = http://ws.agiv.be/crabws/ListOrganisaties
    -> AttributeExposer_10
AttributeExposer_10
    ATTR_LIST = Code,Naam,Definitie
    -> BulkAttributeRenamer_6
BulkAttributeRenamer_6
    PATTERN_ACTION_DISP = Add String Prefix
    ATTRLIST = Code Definitie Naam
    REPLACE_STR = wgobj.BeginOrganisatie_
    ATTRCHOICE = Selected Attributes
    -> BulkAttributeRenamer_10
BulkAttributeRenamer_10
    CASE_DISP = yes
    PATTERN_ACTION_DISP = Remove Suffix String
    ATTRLIST = wgobj.BeginOrganisatie_Code
    REPLACE_STR = _Code
    ATTRCHOICE = Selected Attributes
    -> FeatureMerger_4 [SUPPLIER]
FeatureMerger_4
    PROCESS_DUPS = No
    ATTR_CONFLICT_RES = Use Requestor
    ATTR_ACCUM_MODE = Merge Supplier
    SUPPLIERS_FIRST = No
    JOIN_KEYS = @Value(wgobj.BeginOrganisatie) @Value(wgobj.BeginOrganisatie) AUTO
    IGNORE_NULLS = No
    MERGE_TYPE = Attributes Only
    MERGED -> ParameterFetcher_9
    NOT_MERGED -> FeatureMerger_NotMerged_4
ParameterFetcher_9
    ATTR_LIST = _parameter_AardWegobject {$(AardWegobject)}
    -> TestFilter_9
TestFilter_9
    DEFAULT_VALUE = <UNFILTERED>
    TEST_LIST = BOOL_OP,OR,COMPOSITE_TEST,<Unused>,TEST_CLAUSE,"TEST @Value(_parameter_AardWegobject) MATCHES_REGEX .*(\s|^)@Value(AardWegobject)(\s|$).*",AardWegobject,BOOL_OP,AND,COMPOSITE_TEST,<Unused>,TEST_CLAUSE,"TEST _parameter_AardWegobject ATTRIBUTE_IS_EMPTY """"",no param
    AardWegobject -> BulkAttributeRemover_11
    no param -> BulkAttributeRemover_11
BulkAttributeRemover_11
    ATTR_EXP = ^_parameter_|^_element_
    -> WegObject_extra [off]
FeatureMerger_NotMerged_4: Inspector

Bookmark: ListBewerkingen BeginBewerking
CRABwsCaller_30
    _ws_targeturl = http://crab.agiv.be/wscrab/WsCrab.svc
    _ws_elementstomatch = CodeItem
    _ws_soapbody:
      <soapenv:Envelope xmlns:soapenv="http://schemas.xmlsoap.org/soap/envelope/" xmlns:crab="http://ws.agiv.be/crabws">
         <soapenv:Header/>
         <soapenv:Body>
            <crab:ListBewerkingen>
               <!--Optional:-->
               <crab:SorteerVeld>1</crab:SorteerVeld>
            </crab:ListBewerkingen>
         </soapenv:Body>
      </soapenv:Envelope>
    _ws_contenttype = text/xml;charset=UTF-8
    _ws_soapaction = http://ws.agiv.be/crabws/ListBewerkingen
    -> AttributeExposer_30
AttributeExposer_30
    ATTR_LIST = Code,Naam,Definitie
    -> BulkAttributeRenamer_38
BulkAttributeRenamer_38
    PATTERN_ACTION_DISP = Add String Prefix
    ATTRLIST = Code Definitie Naam
    REPLACE_STR = perc.BeginBewerking_
    ATTRCHOICE = Selected Attributes
    -> BulkAttributeRenamer_40
BulkAttributeRenamer_40
    CASE_DISP = yes
    PATTERN_ACTION_DISP = Remove Suffix String
    ATTRLIST = perc.BeginBewerking_Code
    REPLACE_STR = _Code
    ATTRCHOICE = Selected Attributes
    -> FeatureMerger_18 [SUPPLIER]
FeatureMerger_18
    PROCESS_DUPS = No
    ATTR_CONFLICT_RES = Use Requestor
    ATTR_ACCUM_MODE = Merge Supplier
    SUPPLIERS_FIRST = No
    JOIN_KEYS = @Value(perc.BeginBewerking) @Value(perc.BeginBewerking) AUTO
    IGNORE_NULLS = No
    MERGE_TYPE = Attributes Only
    MERGED -> BulkAttributeRemover_31
    NOT_MERGED -> FeatureMerger_NotMerged_16
BulkAttributeRemover_31
    ATTR_EXP = ^_parameter_|^_element_
    -> FeatureMerger_19 [REQUESTOR]
FeatureMerger_NotMerged_16: Inspector

Bookmark: ListOrganisaties BeginOrganisatie
CRABwsCaller_31
    _ws_targeturl = http://crab.agiv.be/wscrab/WsCrab.svc
    _ws_elementstomatch = CodeItem
    _ws_soapbody:
      <soapenv:Envelope xmlns:soapenv="http://schemas.xmlsoap.org/soap/envelope/" xmlns:crab="http://ws.agiv.be/crabws">
         <soapenv:Header/>
         <soapenv:Body>
            <crab:ListOrganisaties>
               <!--Optional:-->
               <crab:SorteerVeld>1</crab:SorteerVeld>
            </crab:ListOrganisaties>
         </soapenv:Body>
      </soapenv:Envelope>
    _ws_contenttype = text/xml;charset=UTF-8
    _ws_soapaction = http://ws.agiv.be/crabws/ListOrganisaties
    -> AttributeExposer_31
AttributeExposer_31
    ATTR_LIST = Code,Naam,Definitie
    -> BulkAttributeRenamer_39
BulkAttributeRenamer_39
    PATTERN_ACTION_DISP = Add String Prefix
    ATTRLIST = Code Definitie Naam
    REPLACE_STR = perc.BeginOrganisatie_
    ATTRCHOICE = Selected Attributes
    -> BulkAttributeRenamer_41
BulkAttributeRenamer_41
    CASE_DISP = yes
    PATTERN_ACTION_DISP = Remove Suffix String
    ATTRLIST = perc.BeginOrganisatie_Code
    REPLACE_STR = _Code
    ATTRCHOICE = Selected Attributes
    -> FeatureMerger_19 [SUPPLIER]
FeatureMerger_19
    PROCESS_DUPS = No
    ATTR_CONFLICT_RES = Use Requestor
    ATTR_ACCUM_MODE = Merge Supplier
    SUPPLIERS_FIRST = No
    JOIN_KEYS = @Value(perc.BeginOrganisatie) @Value(perc.BeginOrganisatie) AUTO
    IGNORE_NULLS = No
    MERGE_TYPE = Attributes Only
    MERGED -> BulkAttributeRemover_32
    NOT_MERGED -> FeatureMerger_NotMerged_17
BulkAttributeRemover_32
    ATTR_EXP = ^_parameter_|^_element_
    -> VertexCreator
FeatureMerger_NotMerged_17: Inspector

Bookmark: GetPerceel
CRABwsCaller_29
    _ws_targeturl = http://crab.agiv.be/wscrab/WsCrab.svc
    _ws_elementstomatch = GetPerceelByIdentificatorPerceelResult
    _ws_soapbody:
      <soapenv:Envelope xmlns:soapenv="http://schemas.xmlsoap.org/soap/envelope/" xmlns:crab="http://ws.agiv.be/crabws">
         <soapenv:Header/>
         <soapenv:Body>
            <crab:GetPerceelByIdentificatorPerceel>
               <crab:IdentificatorPerceel>@Value(IdentificatorPerceel)</crab:IdentificatorPerceel>
            </crab:GetPerceelByIdentificatorPerceel>
         </soapenv:Body>
      </soapenv:Envelope>
    _ws_contenttype = text/xml;charset=UTF-8
    _ws_soapaction = http://ws.agiv.be/crabws/GetPerceelByIdentificatorPerceel
    -> AttributeExposer_29
AttributeExposer_29
    ATTR_LIST = CenterX,CenterY,BeginDatum,BeginTijd,BeginBewerking,BeginOrganisatie
    -> BulkAttributeRenamer_37
BulkAttributeRenamer_37
    PATTERN_ACTION_DISP = Add String Prefix
    ATTRLIST = BeginBewerking BeginDatum BeginOrganisatie BeginTijd
    REPLACE_STR = perc.
    ATTRCHOICE = Selected Attributes
    -> BulkAttributeRemover_30
BulkAttributeRemover_30
    ATTR_EXP = ^_parameter_|^_element_
    -> FeatureMerger_18 [REQUESTOR]

FME custom transformer CRABwsCaller

Parameters:
- _ws_targeturl = http://crab.agiv.be/wscrab/WsCrab.svc   # Target url CRABws
- _ws_soapbody =   # SOAP Body
- _ws_soapaction =   # SOAP Action
- _ws_elementstomatch =   # Elements to Match
- _ws_contenttype = text/xml;charset=UTF-8

Input (input)
    -> HTTPCaller
Output (output)
HTTPCaller__Rejected_: Inspector

Bookmark: Request CRABws
HTTPCaller
    CONNECTION_TIMEOUT_LENGTH = 60
    TARGET_URL = $(_ws_targeturl)
    CUSTOM_HEADERS = SOAPAction;"$(_ws_soapaction)"  User-Agent;Apache-HttpClient/4.1.1 (java 1.5)  Connection;Keep-Alive
    TARGET_ATTR = _http_response_body
    HTTP_METHOD = POST
    VERIFY_SSL_CERTIFICATES = Yes
    TRANSFER_TIMEOUT_LENGTH = 90
    RESPONSE_HEADER_LIST_ATTR = _http_headers
    ERROR_ATTR = _http_error
    FOLLOW_REDIRECTS = Yes
    STATUS_CODE_ATTR = _http_status_code
    UPLOAD_TYPE = Specify Upload Body
    UPLOAD_CONTENT_TYPE = $(_ws_contenttype)
    UPLOAD_BODY = $(_ws_soapbody)
    USE_COOKIES = No
    TARGET_ATTR_ENCODING = auto-detect
    SAVE_FILE = Attribute
    -> XMLFragmenter
    <Rejected> -> HTTPCaller__Rejected_
XMLFragmenter
    FLATTEN_OPTIONS = <structure separator="." map-empty-elements="yes" matched-prefix="attributes" matched-attributes="yes" cardinality="+{?}" structure-prefix="" child-position-attribute="" except-expression="" ui-mode="basic" matched-ancestor-attributes=""/>
    FEATURE_TYPES_FORMAT_NAME = XML
    EMBEDDED_EXPRESSIONS = $(_ws_elementstomatch)
    ATTRIBUTE_XML = _http_response_body
    MERGE_ATTRS = Yes
    XML_SOURCE_TYPE = Attribute with XML document
    FRAGMENTS -> BulkAttributeRemover
BulkAttributeRemover
    ATTR_EXP = ^_http|^_soap|^_ws|^xml_|^_creation
    -> Output (output)
