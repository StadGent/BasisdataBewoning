FME workspace 000_BEW_KADbasisdata.fmw
Title: 000_BEW_KADbasisdata
Description: Bewerkingen: 
Koppeling kadastrale percelen aan kadastrale leggerinfo KAD_parcel en KAD_owner. 
Categorieën contructionYear en beschrijving nature toevoegen aan KAD_parcel.csv
History: 2016-10-06,Jonas Verstraete,Initial version,2016-10-21,Jonas Verstraete,Update to new cadastre data structure

Parameters:
- DestDataset_FFS = ..\data\intermediate\000\000_KAD.ffs   # Destination FME Feature Store (FFS) File
- SourceDataset_SHAPE_4 = ..\data\input\B_CaPa.shp   # Source Esri Shape File(s)
- MINX =   # Minimum X
- MINY =   # Minimum Y
- MAXX =   # Maximum X
- MAXY =   # Maximum Y
- DestDataset_CSV = ..\data\intermediate\000   # Destination CSV (CommaSeparatedValue) Folder
- SourceDataset_CSV = ..\data\input\KADnature_codelist.csv   # Source CSV (Comma Separated Value) File(s)
- SourceDataset_CSV_4 = ..\data\input\KAD_owner.csv   # Source CSV (Comma Separated Value) File(s)
- SourceDataset_CSV_8 = ..\data\input\KAD_parcel.csv   # Source CSV (Comma Separated Value) File(s)

Readers:
- SHAPE_1: SHAPE from $(SourceDataset_SHAPE_4) in EPSG:31370
- CSV_1: CSV from $(SourceDataset_CSV)
- CSV_2: CSV from $(SourceDataset_CSV_4)
- CSV_3: CSV from $(SourceDataset_CSV_8)

Writers:
- FFS_1: FFS to $(DestDataset_FFS) in EPSG:31370
- CSV_4: CSV to $(DestDataset_CSV)

AttributeRenamer_9
    ATTR_TABLE = RENAME_SET_DEFAULT CAPAKEY > capakey
    -> FeatureMerger_5 [SUPPLIER]
Note: 000_BEW_KADbasisdata.fmw / Bewerkingen: / Koppeling kadastrale percelen aan kadastrale leggerinfo KAD_parcel en KAD_owner. / Categorieën contructionYear en beschrijving nature toevoegen aan KAD_parcel.csv
AttributeValueMapper
    DIRECTION = Forward (Source To Destination)
    VAL_ATTR = bouwjaar
    DEFAULT_VALUE = @Value(constructionYear)
    SRC = constructionYear
    LUT = 0000,verkoop op plan,0001,voor 1850,0002,van 1850 tot 1874,0003,van 1875 tot 1899,0004,van 1900 tot 1918,0005,van 1919 tot 1930
    -> FeatureMerger_2 [REQUESTOR]
AttributeRenamer_7
    ATTR_TABLE = RENAME_SET_DEFAULT Beschrijving_Nl > aard
    -> FeatureMerger_2 [SUPPLIER]
FeatureMerger_2
    PROCESS_DUPS = No
    ATTR_CONFLICT_RES = Use Requestor
    MERGE_TYPE = Attributes Only
    SUPPLIERS_FIRST = No
    JOIN_KEYS = @Value(nature) @Value(Code_aard_nature) AUTO
    IGNORE_NULLS = No
    ATTR_ACCUM_MODE = Merge Supplier
    MERGED -> FeatureMerger_5 [REQUESTOR]
    NOT_MERGED -> FeatureMerger_5 [REQUESTOR]
Note: 1..n op 1 / NiotMerged: error Kadaster Legger-Map koppeling
FeatureMerger_5
    PROCESS_DUPS = Yes
    MERGE_TYPE = Geometry
    SUPPLIERS_FIRST = No
    JOIN_KEYS = @Value(capakey) @Value(capakey) AUTO
    GEOM_TYPE = Build Polygons
    MERGED -> 000_KAD_parcel (writer FFS_1)
    MERGED -> FeatureMerger_6 [SUPPLIER]
    MERGED -> AttributeCreator_3
    NOT_MERGED -> Eigendom_zonder_matching_CaPa
    NOT_MERGED -> AttributeCreator_4
    REFERENCED -> AttributeCreator_8
    UNREFERENCED -> 000_KAD_parcel (writer FFS_1)
    UNREFERENCED -> Perceel_zonder_eigendom
    UNREFERENCED -> AttributeCreator_9
Note: 1..n op 1 / NiotMerged: error Kadaster Legger-Map koppeling
FeatureMerger_6
    PROCESS_DUPS = Yes
    MERGE_TYPE = Geometry
    SUPPLIERS_FIRST = No
    JOIN_KEYS = @Value(propertySituationIdf) @Value(propertySituationIdf) AUTO
    GEOM_TYPE = Build Polygons
    MERGED -> 000_KAD_owner (writer FFS_1)
    MERGED -> AttributeCreator_6
    NOT_MERGED -> AttributeCreator_7
000_KAD_owner (writer FFS_1)
    attributes: propertySituationIdf varchar(9), order varchar(3), partyType varchar(3), right varchar(51), right_trad varchar(51), managedBy number(2,0), officialId varchar(12), name varchar(80), firstname varchar(12), birthdate varchar(11), country varchar(3), zipCode varchar(4), municipality_fr varchar(30), municipality_nl varchar(30), street_fr varchar(30), street_nl varchar(30), number varchar(5), boxNumber varchar(5), officialId_partner varchar(13), name_partner varchar(23), firstName_partner varchar(13), birthdate_partner varchar(11), country_partner varchar(3), zipCode_partner varchar(5), municipality_partner_fr varchar(30), municipality_partner_nl varchar(30), street_partner_fr varchar(30), street_partner_nl varchar(30), number_partner varchar(20), boxNumber_partner varchar(5),
      coOwner varchar(16), anonymousOwner varchar(1), dateSituation varchar(9)
000_KAD_parcel (writer FFS_1)
    attributes: propertySituationIdf number(8,0), divCad number(5,0), section varchar(1), primaryNumber number(4,0), bisNumber number(2,0), exponentLetter varchar(1), exponentNumber number(3,0), partNumber varchar(5), capakey varchar(17), order varchar(4), nature varchar(3), descriptPrivate varchar(35), block varchar(2), floor varchar(2), floorSituation varchar(5), crossDetail varchar(20), matUtil varchar(1), notTaxedMatUtil varchar(3), nisCom varchar(6), street_situation varchar(20), street_translation varchar(1), street_code varchar(6), number varchar(6), polWa varchar(8), surfaceNotTaxable number(10,0), surfaceTaxable number(10,0), surfaceVerif varchar(2), constructionYear number(5,0), soilIndex number(2,0), soilRent varchar(2),
      cadastralIncomePerSurface number(3,0), cadastralIncomePerSurfaceOtherDi number(2,0), numberCadastralIncome number(1,0), charCadastralIncome varchar(1), cadastralIncome number(8,0), dateEndExoneration varchar(1), decrete varchar(1), constructionIndication number(4,0), constructionType varchar(2), floorNumberAboveground number(2,0), garret number(2,0), physModYear number(5,0), constructionQuality varchar(2), garageNumber number(3,0), centralHeating number(3,0), bathroomNumber number(3,0), housingUnitNumber number(2,0), placeNumber number(4,0), builtSurface number(5,0), usedSurface number(5,0), dateSituation varchar(9), aard varchar(10), bouwjaar varchar(25)
Note: Eigendom zonder matching CaPa perceel / Geen geometrie. Zal niet verder worden gebruikt.
Eigendom_zonder_matching_CaPa: Inspector
Note: Parcel zonder eigendom / Worden bij gebouwtype als 'Andere' geclassificeerd.
Perceel_zonder_eigendom: Inspector

Bookmark: INPUT: Kadaster Legger Nieuwe structuur owner
B_CaPa (reader SHAPE_1)
    attributes: CAPAKEY char(17), CAPATY char(2), SHAPE_AREA number(12,4), SHEET char(18)
    -> AttributeRenamer_9

Bookmark: INPUT: Kadaster Legger Nieuwe structuur owner
KAD_owner (reader CSV_2)
    attributes: propertySituationIdf number(9,0), order number(3,0), partyType number(3,0), right char(51), right_trad char(51), managedBy number(2,0), officialId number(13,0), name char(80), firstname char(12), birthdate char(11), country char(3), zipCode char(8), municipality_fr char(25), municipality_nl char(25), street_fr char(34), street_nl char(33), number char(5), boxNumber char(5), officialId_partner number(13,0), name_partner char(23), firstName_partner char(13), birthdate_partner char(11), country_partner char(3), zipCode_partner number(5,0), municipality_partner_fr char(19), municipality_partner_nl char(19), street_partner_fr char(23), street_partner_nl char(23), number_partner number(4,0), boxNumber_partner char(5),
      coOwner char(18), anonymousOwner char(1), dateSituation char(9)
    -> FeatureMerger_6 [REQUESTOR]

Bookmark: INPUT: Kadaster Legger Nieuwe structuur parcel
KAD_parcel (reader CSV_3)
    attributes: propertySituationIdf number(10,0), divCad number(6,0), section char(2), primaryNumber number(5,0), bisNumber number(3,0), exponentLetter char(2), exponentNumber number(3,0), partNumber char(6), capakey char(18), order number(3,0), nature number(4,0), descriptPrivate char(20), block char(2), floor char(1), floorSituation char(1), crossDetail char(11), matUtil char(1), notTaxedMatUtil char(3), nisCom number(6,0), street_situation char(23), street_translation char(1), street_code number(6,0), number char(11), polWa char(8), surfaceNotTaxable number(5,0), surfaceTaxable number(6,0), surfaceVerif char(2), constructionYear number(5,0), soilIndex char(1), soilRent char(2),
      cadastralIncomePerSurface number(3,0), cadastralIncomePerSurfaceOtherDi number(2,0), numberCadastralIncome number(2,0), charCadastralIncome char(2), cadastralIncome number(6,0), dateEndExoneration char(1), decrete char(1), constructionIndication number(4,0), constructionType char(2), floorNumberAboveground number(2,0), garret number(2,0), physModYear number(5,0), constructionQuality char(2), garageNumber number(3,0), centralHeating number(2,0), bathroomNumber number(3,0), housingUnitNumber number(3,0), placeNumber number(3,0), builtSurface number(5,0), usedSurface number(5,0), dateSituation char(9)
    -> AttributeValueMapper

Bookmark: Metadata KAD nieuwe structuur
KADnature_codelist (reader CSV_1)
    attributes: Code_aard_nature number(4,0), Description_Fr char(21), Beschrijving_Nl char(19)
    -> AttributeRenamer_7

Bookmark: Stats KAD Parcel
AttributeCreator_6
    ATTR_TABLE = SET_TO Type = Merged to Parcel by PropertySituationId
    -> StatisticsCalculator_2
AttributeCreator_7
    ATTR_TABLE = SET_TO Type = NotMerged to Parcel: no matching PropertySituationId
    -> StatisticsCalculator_2
StatisticsCalculator_2
    COUNT_ATTR = Total
    COMPUTE_HISTOGRAM = NO
    PREPEND_ATTR_NAME_CHOICE = For multiple results only
    STATS_ATTRS = propertySituationIdf
    COMPLETE -> StatisticsCalculator_5
StatisticsCalculator_5
    COUNT_ATTR = Count
    COMPUTE_HISTOGRAM = NO
    PREPEND_ATTR_NAME_CHOICE = For multiple results only
    GROUP_BY = Type Total
    STATS_ATTRS = propertySituationIdf
    SUMMARY -> AttributeCreator_5
AttributeCreator_5
    ATTR_LIST = Pct,@Evaluate(100*@Value(Count)/@Value(Total))
    -> 000_Stats_KADowner (writer CSV_4)
000_Stats_KADowner (writer CSV_4)
    attributes: Type char(100), Count number(10,0), Pct number(10,6), Total number(10,0)

Bookmark: Stats KAD Parcel
AttributeCreator_3
    ATTR_TABLE = SET_TO Type = Merged to CaPa on capakey
    -> StatisticsCalculator_3
AttributeCreator_4
    ATTR_TABLE = SET_TO Type = NotMerged to CaPa: no matching capakey
    -> StatisticsCalculator_3
StatisticsCalculator_3
    COUNT_ATTR = Total
    COMPUTE_HISTOGRAM = NO
    PREPEND_ATTR_NAME_CHOICE = For multiple results only
    STATS_ATTRS = propertySituationIdf
    COMPLETE -> StatisticsCalculator_4
StatisticsCalculator_4
    COUNT_ATTR = Count
    COMPUTE_HISTOGRAM = NO
    PREPEND_ATTR_NAME_CHOICE = For multiple results only
    GROUP_BY = Type Total
    STATS_ATTRS = propertySituationIdf
    SUMMARY -> AttributeCreator_21
AttributeCreator_21
    ATTR_LIST = Pct,@Evaluate(100*@Value(Count)/@Value(Total))
    -> 000_Stats_KADparcel (writer CSV_4)
AttributeCreator_8
    ATTR_TABLE = SET_TO Type = Referenced CaPa: matching KADinfo found
    -> StatisticsCalculator_6
AttributeCreator_9
    ATTR_TABLE = SET_TO Type = Not Referenced CaPa: no matching KADinfo
    -> StatisticsCalculator_6
StatisticsCalculator_6
    COUNT_ATTR = Total
    COMPUTE_HISTOGRAM = NO
    PREPEND_ATTR_NAME_CHOICE = For multiple results only
    STATS_ATTRS = capakey
    COMPLETE -> StatisticsCalculator_7
StatisticsCalculator_7
    COUNT_ATTR = Count
    COMPUTE_HISTOGRAM = NO
    PREPEND_ATTR_NAME_CHOICE = For multiple results only
    GROUP_BY = Type Total
    STATS_ATTRS = capakey
    SUMMARY -> AttributeCreator_10
AttributeCreator_10
    ATTR_LIST = Pct,@Evaluate(100*@Value(Count)/@Value(Total))
    -> 000_Stats_KADparcel (writer CSV_4)
000_Stats_KADparcel (writer CSV_4)
    attributes: Type char(100), Count number(10,0), Pct number(10,6), Total number(10,0)
