FME workspace BATCH_BEW.fmw
Title: BATCH_BEW
Description: Gebruik deze workspace om alle processen (000-005) van het dataproces Basisdata Bewoning na elkaar te laten lopen.
History: 2016-10-06,Jonas Verstraete,Initial version,2016-10-21,Jonas Verstraete,Update new cadastre data structure

Parameters:
- Toestand = 20160101   # Toestand (%Y%m%d)
- GeolocatorRequestURL =   # " " Attribute Value
- municipality =   # Municipality
- language = nl   # Municipality language

Note: BEW_BATCH.fmw / Gebruik deze workspace om alle processen (000-005) van het dataproces Basisdata Bewoning na elkaar te laten lopen.
Creator
    GEOMTYPE = Geometry Object
    NUM = 1
    CREATED -> WorkspaceRunner_000
WorkspaceRunner_8_Succeeded: Inspector

Bookmark: 000_BEW_BevRegbasisdata
WorkspaceRunner_000
    WORKSPACE_FILE = 000_BEW_BevRegbasisdata.fmw
    BLOCKING = Yes
    WORKSPACE_PARAMETERS = DestDataset_FFS,..\data\intermediate\000\000_BevReg.ffs,SourceDataset_CSV_4,..\data\input\BevReg_extr.csv,SourceDataset_CSV,..\data\input\CRAB_RijksregisterStraat.csv
    SUCCEEDED -> WorkspaceRunner_2
    FAILED -> WorkspaceRunner_Failed
WorkspaceRunner_Failed: Inspector

Bookmark: 000_BEW_CRABbasisdata
WorkspaceRunner_2
    WORKSPACE_FILE = 000_BEW_CRABbasisdata.fmw
    BLOCKING = Yes
    WORKSPACE_PARAMETERS = Toestand,$(Toestand),DestDataset_SHAPE,..\data\intermediate\000,DestDataset_FFS,..\data\intermediate\000\000_CRAB_alladr.ffs,SourceDataset_CSV_10,..\data\input\huisnummer.csv,SourceDataset_CSV,..\data\input\subadres.csv,SourceDataset_CSV_9,..\data\input\adrespositie.csv,SourceDataset_CSV_11,..\data\input\straatnaam.csv,SourceDataset_CSV_7,..\data\input\postkantoncode.csv
    SUCCEEDED -> WorkspaceRunner_3
    FAILED -> WorkspaceRunner_Failed_2
WorkspaceRunner_Failed_2: Inspector

Bookmark: 000_BEW_KADbasisdata
WorkspaceRunner_3
    WORKSPACE_FILE = 000_BEW_KADbasisdata.fmw
    BLOCKING = Yes
    WORKSPACE_PARAMETERS = DestDataset_FFS,..\data\intermediate\000\000_KAD.ffs,SourceDataset_SHAPE_4,..\data\input\B_CaPa.shp,MINX,,MINY,,MAXX,,MAXY,,DestDataset_CSV,..\data\intermediate\000,SourceDataset_CSV,..\data\input\KADnature_codelist.csv,SourceDataset_CSV_4,..\data\input\KAD_owner.csv,SourceDataset_CSV_8,..\data\input\KAD_parcel.csv
    SUCCEEDED -> WorkspaceRunner_4
    FAILED -> WorkspaceRunner_Failed_3
WorkspaceRunner_Failed_3: Inspector

Bookmark: 001_BEW_BevolkingsReg_CRAB
WorkspaceRunner_4
    WORKSPACE_FILE = 001_BEW_BevolkingsReg_CRAB.fmw
    BLOCKING = Yes
    WORKSPACE_PARAMETERS = DestDataset_SHAPE,..\data\intermediate\001,DestDataset_CSV,..\data\intermediate\001,SourceDataset_FFS,..\data\intermediate\000\000_CRAB_alladr.ffs,SourceDataset_FFS_4,..\data\intermediate\000\000_BevReg.ffs,DestDataset_FFS,..\data\intermediate\001\001_BevReg_CRAB.ffs,DestDataset_FFS_2,..\data\intermediate\001\001_BevReg_adr_notCRAB.ffs,MINX,,MINY,,MAXX,,MAXY,,GeolocatorRequestURL,$(GeolocatorRequestURL)
    SUCCEEDED -> WorkspaceRunner_5
    FAILED -> WorkspaceRunner_Failed_4
WorkspaceRunner_Failed_4: Inspector

Bookmark: 002_BEW_KAD_CRAB_MATCH
WorkspaceRunner_5
    WORKSPACE_FILE = 002_BEW_KAD_CRAB_MATCH.fmw
    BLOCKING = Yes
    WORKSPACE_PARAMETERS = SourceDataset_SHAPE_5,..\data\input\CRAB_Percelen_CenterPoints.shp,DestDataset_CSV_3,..\data\intermediate\002,SourceDataset_SHAPE_4,..\data\input\B_CaPa.shp,MINX,,MINY,,MAXX,,MAXY,,SourceDataset_FFS_6,..\data\intermediate\000\000_CRAB_alladr.ffs,DestDataset_FFS,..\data\intermediate\002\002_CRAB_alladr_capakey.ffs,DestDataset_ESRISHAPE,..\data\intermediate\002,SourceDataset_FFS,..\data\intermediate\001\001_BevReg_adr_notCRAB.ffs,SourceDataset_FFS_7,..\data\intermediate\000\000_KAD.ffs
    SUCCEEDED -> WorkspaceRunner_6
    FAILED -> WorkspaceRunner_Failed_5
WorkspaceRunner_Failed_5: Inspector

Bookmark: 003_BEW_Wooneenheden
WorkspaceRunner_6
    WORKSPACE_FILE = 003_BEW_Wooneenheden.fmw
    BLOCKING = Yes
    WORKSPACE_PARAMETERS = MINX,,MINY,,MAXX,,MAXY,,SourceDataset_FFS_4,..\data\intermediate\002\002_CRAB_alladr_capakey.ffs,SourceDataset_FFS_5,..\data\intermediate\001\001_BevReg_CRAB.ffs,DestDataset_FFS,..\data\intermediate\003\003_Huishoudens.ffs,DestDataset_FFS_2,..\data\intermediate\003\003_Gebouweenheden_Adressen.ffs,DestDataset_FFS_3,..\data\intermediate\003\003_KADparcel_Gebouweenheden.ffs,DestDataset_ESRISHAPE,..\data\intermediate\003,SourceDataset_FFS,..\data\intermediate\000\000_KAD.ffs,SourceDataset_Handelspanden,..\data\input\Handelspanden.shp
    SUCCEEDED -> WorkspaceRunner_7
    FAILED -> WorkspaceRunner_Failed_6
WorkspaceRunner_Failed_6: Inspector

Bookmark: 004_BEW_Eigenaars
WorkspaceRunner_7
    WORKSPACE_FILE = 004_BEW_Eigenaars.fmw
    BLOCKING = Yes
    WORKSPACE_PARAMETERS = SourceDataset_FFS_9,..\data\intermediate\001\001_BevReg_adr_notCRAB.ffs,MINX,,MINY,,MAXX,,MAXY,,SourceDataset_FFS_14,..\data\intermediate\001\001_BevReg_CRAB.ffs,municipality,$(municipality),language,$(language),SourceDataset_FFS_13,..\data\intermediate\000\000_CRAB_alladr.ffs,DestDataset_FFS_2,..\data\intermediate\004\004_KAD_owner.ffs,DestDataset_FFS_3,..\data\intermediate\004\004_Gebouweenheden_Adressen.ffs,SourceDataset_FFS_6,..\data\intermediate\003\003_Gebouweenheden_Adressen.ffs,DestDataset_FFS,..\data\intermediate\004\004_KAD_percelen.ffs,SourceDataset_FFS,..\data\intermediate\003\003_KADparcel_Gebouweenheden.ffs,SourceDataset_FFS_12,..\data\intermediate\000\000_KAD.ffs
    SUCCEEDED -> WorkspaceRunner_8
    FAILED -> WorkspaceRunner_Failed_7
WorkspaceRunner_Failed_7: Inspector

Bookmark: 005_BEW_CopyToOutput
WorkspaceRunner_8
    WORKSPACE_FILE = 005_BEW_CopyToOutput.fmw
    BLOCKING = Yes
    WORKSPACE_PARAMETERS = SourceDataset_FFS,..\data\intermediate\001\001_BevReg_CRAB.ffs,SourceDataset_FFS_9,..\data\intermediate\003\003_Huishoudens.ffs,SourceDataset_FFS_13,..\data\intermediate\002\002_CRAB_alladr_capakey.ffs,DestDataset_FFS,..\data\output\BEW_Inwoners.ffs,DestDataset_ESRISHAPE,..\data\output,DestDataset_FFS_2,..\data\output\BEW_Huishoudens.ffs,DestDataset_FFS_3,..\data\output\BEW_Adressen.ffs,DestDataset_FFS_4,..\data\output\BEW_Gebouweenheden_Adressen.ffs,DestDataset_FFS_5,..\data\output\BEW_Percelen.ffs,DestDataset_FFS_6,..\data\output\BEW_Eigendommen.ffs,DestDataset_FFS_11,..\data\output\BEW_Eigenaars.ffs,SourceDataset_FFS_14,..\data\intermediate\004\004_Gebouweenheden_Adressen.ffs,SourceDataset_FFS_10,..\data\intermediate\004\004_KAD_percelen.ffs,SourceDataset_FFS_11,..\data\intermediate\000\000_KAD.ffs,SourceDataset_FFS_8,..\data\intermediate\004\004_KAD_owner.ffs
    SUCCEEDED -> WorkspaceRunner_8_Succeeded
    FAILED -> WorkspaceRunner_Failed_8
WorkspaceRunner_Failed_8: Inspector
