FME workspace 002_BEW_KAD_CRAB_MATCH.fmw
Title: 002_BEW_KAD_CRAB_MATCH.fmw
Description: Bewerkingen: 
 Toekennen van Capakey (perceel) aan CRAB adressen obv CRAB-percelen koppeling en geografische doordruk.
History: 2016-10-06,Jonas Verstraete,Initial version,2016-10-21,Jonas Verstraete,Update to new cadastre datastructure

Parameters:
- SourceDataset_SHAPE_5 = ..\data\input\CRAB_Percelen_CenterPoints.shp   # Source Esri Shape File(s)
- DestDataset_CSV_3 = ..\data\intermediate\002   # Destination CSV (CommaSeparatedValue) Folder
- SourceDataset_SHAPE_4 = ..\data\input\B_CaPa.shp   # Source Esri Shape File(s)
- MINX =   # Minimum X
- MINY =   # Minimum Y
- MAXX =   # Maximum X
- MAXY =   # Maximum Y
- SourceDataset_FFS_6 = ..\data\intermediate\000\000_CRAB_alladr.ffs   # Source FME Feature Store (FFS) File(s)
- DestDataset_FFS = ..\data\intermediate\002\002_CRAB_alladr_capakey.ffs   # Destination FME Feature Store (FFS) File
- DestDataset_ESRISHAPE = ..\data\intermediate\002   # Destination Esri Shapefile Folder
- SourceDataset_FFS = ..\data\intermediate\001\001_BevReg_adr_notCRAB.ffs   # Source FME Feature Store (FFS) File(s)
- SourceDataset_FFS_7 = ..\data\intermediate\000\000_KAD.ffs   # Source FME Feature Store (FFS) File(s)

Readers:
- FFS_1: FFS from $(SourceDataset_FFS)
- SHAPE_1: SHAPE from $(SourceDataset_SHAPE_5)
- SHAPE_2: SHAPE from $(SourceDataset_SHAPE_4)
- FFS_2: FFS from $(SourceDataset_FFS_6)
- FFS_3: FFS from $(SourceDataset_FFS_7)

Writers:
- CSV_1: CSV to $(DestDataset_CSV_3)
- FFS_4: FFS to $(DestDataset_FFS) in EPSG:31370
- ESRISHAPE_1: ESRISHAPE to $(DestDataset_ESRISHAPE)

Note: 002_BEW_KAD_CRAB_MATCH.fmw / Bewerkingen: / Toekennen van Capakey (perceel) aan CRAB adressen o.b.v. CRAB-percelen koppeling en geografische doordruk.
000_KAD_parcel (reader FFS_3) [off]
    attributes: propertySituationIdf number(8,0), divCad number(5,0), section varchar(1), primaryNumber number(4,0), bisNumber number(2,0), exponentLetter varchar(1), exponentNumber number(3,0), partNumber varchar(5), capakey varchar(17), order varchar(4), nature varchar(3), descriptPrivate varchar(35), block varchar(2), floor varchar(2), floorSituation varchar(5), crossDetail varchar(20), matUtil varchar(1), notTaxedMatUtil varchar(3), nisCom varchar(6), street_situation varchar(20), street_translation varchar(1), street_code varchar(6), number varchar(6), polWa varchar(8), surfaceNotTaxable number(10,0), surfaceTaxable number(10,0), surfaceVerif varchar(2), constructionYear number(5,0), soilIndex number(2,0), soilRent varchar(2),
      cadastralIncomePerSurface number(3,0), cadastralIncomePerSurfaceOtherDi number(2,0), numberCadastralIncome number(1,0), charCadastralIncome varchar(1), cadastralIncome number(8,0), dateEndExoneration varchar(1), decrete varchar(1), constructionIndication number(4,0), constructionType varchar(2), floorNumberAboveground number(2,0), garret number(2,0), physModYear number(5,0), constructionQuality varchar(2), garageNumber number(3,0), centralHeating number(3,0), bathroomNumber number(3,0), housingUnitNumber number(2,0), placeNumber number(4,0), builtSurface number(5,0), usedSurface number(5,0), dateSituation varchar(9), aard varchar(10), bouwjaar varchar(25)
    -> FeatureMerger_4 [REQUESTOR]
B_CaPa (reader SHAPE_2)
    attributes: CAPAKEY char(17), CAPATY char(2), SHAPE_AREA number(12,4), SHEET char(18)
    -> FeatureMerger_4 [SUPPLIER]
    -> AttributeRenamer_7
    -> FeatureMerger_3 [SUPPLIER]
Note: 1..n op 1 / NiotMerged: error Kadaster Legger-Map koppeling
FeatureMerger_4 [off]
    GEOM_TYPE = Build Polygons
    ATTR_ACCUM_MODE = Merge Supplier
    JOIN_KEYS = @Value(capakey) @Value(CAPAKEY) AUTO
    PROCESS_DUPS = Yes
    ATTR_CONFLICT_RES = Use Requestor
    SUPPLIERS_FIRST = No
    IGNORE_NULLS = No
    MERGE_TYPE = Attributes Only
    MERGED -> FeatureMerger_4_Merged
    MERGED -> FeatureMerger_5 [SUPPLIER] [off]
    NOT_MERGED -> FeatureMerger_4_NotMerged
    REFERENCED -> FeatureMerger_4_Referenced
    UNREFERENCED -> FeatureMerger_4_Unreferenced
    DUPLICATE_SUPPLIER -> FeatureMerger_4_DuplicateSupplier
FeatureMerger_4_Merged: Inspector
FeatureMerger_4_NotMerged: Inspector
FeatureMerger_4_Referenced: Inspector
FeatureMerger_4_Unreferenced: Inspector
FeatureMerger_4_DuplicateSupplier: Inspector
Note: CRAB huisnr + subnummers
000_CRAB_alladr (reader FFS_2)
    attributes: CRABadrID varchar(10), STRAATNMID number(11,0), STRAATNM varchar(255), HUISNRID number(11,0), HUISNR varchar(10), HUISNR_BEG varchar(20), HUISNR_TIJ varchar(20), HUISNR_EIN varchar(20), SUBADRESID number(11,0), SUBADRES varchar(255), SUBADR_BEG varchar(20), AARDSUBADR number(11,0), NISGEMCODE varchar(5), PKANCODE number(11,0), GEMNM varchar(4), AARDADRPOS number(11,0), X number(31,15), Y number(31,15), SUBADR_TIJ varchar(20), SUBADR_EIN varchar(20)
    -> AttributeCreator
AttributeCreator
    ATTR_TABLE = SET_TO _adrType = CRAB
    -> FeatureMerger_2 [REQUESTOR]
Note: Extra adressen obv KAD
001_BevReg_adr_notCRAB (reader FFS_1)
    attributes: POSTKODE varchar(4), STRAATKODE varchar(8), NUMMER varchar(5), INDEX varchar(5), sector varchar(5), stadsdeel varchar(16), wijknaam varchar(30), CRAB_merge varchar(254), CRABadrID varchar(10), GEMNM varchar(4), HUISNR varchar(10), PKANCODE number(11,0), STRAATNM varchar(255), SUBADRES varchar(255), adrType varchar(4)
    -> AttributeCreator_2
AttributeCreator_2
    ATTR_TABLE = SET_TO _adrType = BevReg
    -> FeatureMerger_2 [REQUESTOR]
Note: Extra adressen obv KAD / * KAD adres dat enkel op hoofdadres (STRAAT en HUISNR) met CRAB gematched / >> als afzonderlijk adres beschouwd (verschillend SUBNUMMER) - HFD00000 zodat / * KAD adres dat eerst door geolocator (match>90) en nadien gematched op STRAAT en HUISNR / >> KAD adressen zijn gecorrigeerd. bvb 5A > 5, ...: als afzonderlijk adres beschouwd - COR00000 / *Adres dat na geocoderen niet meer kan gemerged aan CRAB-adres / (No clean data: adres BevReg niet in GRAB, wel in CRAB geolocator? Te onderzoeken) / >> Nieuwe CRAB_adrID aangemaakt (GL0000)
Note: CRAB_Percelen_CenterPoints
CRAB_Percelen_CenterPoints (reader SHAPE_1)
    attributes: Gewest char(40), NISCode char(10), Gemeente char(40), Straat char(50), Huisnr char(5), hsnrstatus char(40), capakey char(32), CenterX number(20,10), CenterY number(20,10)
    -> FeatureMerger_2 [SUPPLIER]
Note: NotMerged: CRAB zonder adm CRAB capakey - oorzaak verschil toestand? geen historiek CAPAKEY's / Unreferenced: geen belang. Mogelijk verschil toestand
FeatureMerger_2
    ATTR_ACCUM_MODE = Merge Supplier
    JOIN_KEYS = @Value(STRAATNM) @Value(Straat) AUTO @Value(HUISNR) @Value(Huisnr) AUTO
    PROCESS_DUPS = No
    ATTR_CONFLICT_RES = Use Requestor
    SUPPLIERS_FIRST = No
    IGNORE_NULLS = No
    MERGE_TYPE = Attributes Only
    MERGED -> AttributeRenamer_8
    MERGED -> AttributeCreator_3
    NOT_MERGED -> PointOnAreaOverlayer_2 [POINT]
    NOT_MERGED -> AttributeCreator_4
Note: PERC - CRAB / 0..1 op 0..n
AttributeRenamer_8
    ATTR_LIST = capakey,CRABcapakey,
    -> PointOnAreaOverlayer_2 [POINT]
AttributeCreator_10
    ATTR_LIST = Type,geoCAPAKEY != CRABcapakey,CAPAKEY,@Value(geoCAPAKEY),Omschrijving,Gebruik geografische CAPAKEY onderliggend perceel
    -> PassThrough_2
    -> PassThrough
Note: Lijst legger / Lijst adressen / Vergelijking beide
FeatureMerger_5 [off]
    ATTR_ACCUM_MODE = Merge Supplier
    JOIN_KEYS = @Value(CAPAKEY) @Value(CAPAKEY) AUTO
    PROCESS_DUPS = No
    ATTR_CONFLICT_RES = Use Requestor
    SUPPLIERS_FIRST = No
    IGNORE_NULLS = No
    MERGE_TYPE = Attributes Only
    MERGED -> FeatureMerger_5_Merged
    NOT_MERGED -> FeatureMerger_5_NotMerged
    REFERENCED -> FeatureMerger_5_Referenced
    UNREFERENCED -> FeatureMerger_5_Unreferenced
    DUPLICATE_SUPPLIER -> FeatureMerger_5_DuplicateSupplier
FeatureMerger_5_Merged: Inspector
FeatureMerger_5_NotMerged: Inspector
FeatureMerger_5_Referenced: Inspector
FeatureMerger_5_Unreferenced: Inspector
FeatureMerger_5_DuplicateSupplier: Inspector
002_CRAB_alladr_capakey (writer FFS_4)
    attributes: CRABadrID varchar(10), STRAATNMID number(11,0), STRAATNM varchar(255), HUISNRID number(11,0), HUISNR varchar(10), HUISNR_BEG varchar(20), HUISNR_TIJ varchar(20), HUISNR_EIN varchar(20), SUBADRESID number(11,0), SUBADRES varchar(255), SUBADR_BEG varchar(20), AARDSUBADR number(11,0), NISGEMCODE varchar(5), PKANCODE number(11,0), GEMNM varchar(4), AARDADRPOS number(11,0), X number(31,15), Y number(31,15), SUBADR_TIJ varchar(20), SUBADR_EIN varchar(20), Type varchar(150), Omschrijving varchar(150), CAPAKEY varchar(30), CRABcapa varchar(30), geoCAPAKEY varchar(30)
AttributeRenamer_2
    ATTR_LIST = CRABcapakey,CRABcapa,,Omschrijving,Omschrijvi,
    -> 002_CRAB_alladr_capakey (writer ESRISHAPE_1)
002_CRAB_alladr_capakey (writer ESRISHAPE_1)
    attributes: CRABadrID char(10), STRAATNMID number(11,0), STRAATNM char(254), HUISNRID number(11,0), HUISNR char(10), HUISNR_BEG char(20), HUISNR_TIJ char(20), HUISNR_EIN char(20), SUBADRESID number(11,0), SUBADRES char(254), SUBADR_BEG char(20), AARDSUBADR number(11,0), NISGEMCODE char(5), PKANCODE number(11,0), GEMNM char(4), AARDADRPOS number(11,0), X number(31,15), Y number(31,15), SUBADR_TIJ char(20), SUBADR_EIN char(20), Type char(150), Omschrijvi char(150), CAPAKEY char(30), CRABcapa char(30), geoCAPAKEY char(30)

Bookmark: Stats CRABgeoCapakeyMatch
AttributeRenamer_7
    ATTR_LIST = CAPAKEY,geoCAPAKEY,
    -> PointOnAreaOverlayer_2 [AREA]
Note: NoOverlap: CRAB zonder geo perceel
PointOnAreaOverlayer_2
    POLYS_FIRST = NO
    ATTR_CONFLICT_RES = Use Original
    OV_ATTR = _overlaps
    ATTR_ACCUM_MODE = Merge Incoming
    POINT -> TestFilter
TestFilter
    DEFAULT_VALUE = <UNFILTERED>
    TEST_LIST:
      BOOL_OP,AND,COMPOSITE_TEST,<Unused>,TEST_CLAUSE,"TEST geoCAPAKEY ATTRIBUTE_IS_MISSING """"
      TEST CRABcapakey ATTRIBUTE_IS_MISSING """"",geoCAPAKEY and CRABcapakey MISSING,BOOL_OP,OR,COMPOSITE_TEST,<Unused>,TEST_CLAUSE,"TEST geoCAPAKEY ATTRIBUTE_IS_MISSING """"",geoCAPAKEY MISSING,BOOL_OP,OR,COMPOSITE_TEST,<Unused>,TEST_CLAUSE,"TEST CRABcapakey ATTRIBUTE_IS_MISSING """"",CRABcapakey MISSING,BOOL_OP,OR,COMPOSITE_TEST,<Unused>,TEST_CLAUSE,"TEST @Value(geoCAPAKEY) = @Value(CRABcapakey)",@Value(geoCAPAKEY) = @Value(CRABcapakey)
    geoCAPAKEY and CRABcapakey MISSING -> AttributeCreator_6
    geoCAPAKEY MISSING -> FeatureMerger_3 [REQUESTOR]
    CRABcapakey MISSING -> AttributeCreator_8
    @Value(geoCAPAKEY) = @Value(CRABcapakey) -> AttributeCreator_9
    <UNFILTERED> -> AttributeCreator_10
Note: CRAB zonder PERC
AttributeCreator_6
    ATTR_LIST = Type,geoCAPAKEY missing EN CRABcapakey missing,Omschrijving,CRAB punt zonder perceel
    -> PassThrough_2
    -> PassThrough
Note: 0..1 op 0..n / NotMerged:CRAB capakey incorrect / Unreferenced: Perceel zonder CRAB
FeatureMerger_3
    GEOM_TYPE = Build Polygons
    ATTR_ACCUM_MODE = Merge Supplier
    JOIN_KEYS = @Value(CRABcapakey) @Value(CAPAKEY) AUTO
    PROCESS_DUPS = Yes
    ATTR_CONFLICT_RES = Use Requestor
    SUPPLIERS_FIRST = No
    IGNORE_NULLS = No
    MERGE_TYPE = Attributes Only
    MERGED -> AttributeCreator_7
    NOT_MERGED -> AttributeCreator_12
Note: adm CRAB capakey
AttributeCreator_7
    ATTR_LIST = Type,geoCAPAKEY missing,CAPAKEY,@Value(CRABcapakey),Omschrijving,Gebruik administratieve CRAB capakey
    -> PassThrough_2
    -> PassThrough
Note: adm CRAB capakey incorrect
AttributeCreator_12
    ATTR_LIST = Type,geoCAPAKEY missing EN CRABcapakey incorrect,Omschrijving,Geen correcte perceelsmatch - CRAB zonder perceel
    -> PassThrough_2
    -> PassThrough
Note: geo PERC CAPAKEY
AttributeCreator_8
    ATTR_LIST = Type,CRABcapakey missing,CAPAKEY,@Value(geoCAPAKEY),Omschrijving,Gebruik geografische CAPAKEY onderliggend perceel
    -> PassThrough_2
    -> PassThrough
AttributeCreator_9
    ATTR_LIST = Type,geoCAPAKEY = CRABcapakey,CAPAKEY,@Value(geoCAPAKEY),Omschrijving,Geografische = administratieve CAPAKEY
    -> PassThrough_2
    -> PassThrough
PassThrough: Tester
    TEST_DESCRIPTION = ""
    TEST_MODE = Automatic
    TEST_CLAUSE = TEST 0 = 0
    BOOL_OP = OR
    PASSED -> StatisticsCalculator_4
StatisticsCalculator_4
    COUNT_ATTR = _TotAdrCount
    STATS_ATTRS = CRABadrID
    COMPUTE_HISTOGRAM = NO
    PREPEND_ATTR_NAME_CHOICE = For multiple results only
    GROUP_BY = _adrType
    COMPLETE -> StatisticsCalculator_3
StatisticsCalculator_3
    COUNT_ATTR = _AdrCount
    STATS_ATTRS = CRABadrID
    COMPUTE_HISTOGRAM = NO
    PREPEND_ATTR_NAME_CHOICE = For multiple results only
    GROUP_BY = _adrType _TotAdrCount Type Omschrijving
    SUMMARY -> AttributeCreator_11
AttributeCreator_11
    ATTR_LIST = _AdrPct,@Evaluate(@Value(_AdrCount)*100.00/@Value(_TotAdrCount))
    -> 002_Stats_CAPAKEYquality (writer CSV_1)
002_Stats_CAPAKEYquality (writer CSV_1)
    attributes: _adrType char(100), Type char(100), Omschrijving char(150), _AdrCount number(10,0), _AdrPct number(10,6), _TotAdrCount number(10,0)
PassThrough_2: Tester
    TEST_DESCRIPTION = ""
    TEST_MODE = Automatic
    TEST_CLAUSE = TEST 0 = 0
    BOOL_OP = OR
    PASSED -> AttributeRenamer_9
    PASSED -> AttributeRenamer_2
AttributeRenamer_9
    ATTR_LIST = CRABcapakey,CRABcapa,
    -> 002_CRAB_alladr_capakey (writer FFS_4)
    -> FeatureMerger_5 [REQUESTOR] [off]

Bookmark: Stats CRABpercMatch
AttributeCreator_3
    ATTR_LIST = CRAB_percmatch,Merged
    -> StatisticsCalculator_2
AttributeCreator_4
    ATTR_LIST = CRAB_percmatch,NotMerged
    -> StatisticsCalculator_2
StatisticsCalculator_2
    COUNT_ATTR = _TotAdrCount
    STATS_ATTRS = CRABadrID
    COMPUTE_HISTOGRAM = NO
    PREPEND_ATTR_NAME_CHOICE = For multiple results only
    GROUP_BY = _adrType
    COMPLETE -> StatisticsCalculator
StatisticsCalculator
    COUNT_ATTR = _AdrCount
    STATS_ATTRS = CRABadrID
    COMPUTE_HISTOGRAM = NO
    PREPEND_ATTR_NAME_CHOICE = For multiple results only
    GROUP_BY = _adrType CRAB_percmatch _TotAdrCount
    SUMMARY -> AttributeCreator_5
AttributeCreator_5
    ATTR_LIST = _AdrPct,@Evaluate(@Value(_AdrCount)*100.00/@Value(_TotAdrCount))
    -> AttributeCreator_5_Output
    -> 002_Stats_CRABpercMatch (writer CSV_1)
002_Stats_CRABpercMatch (writer CSV_1)
    attributes: _adrType char(5), CRAB_percmatch char(150), _AdrCount number(10,0), _AdrPct number(10,6), _TotAdrCount number(10,0)
AttributeCreator_5_Output: Inspector

Bookmark: INPUT: CRAB
Note: CRAB toestand: einddatums - geen begindatums
