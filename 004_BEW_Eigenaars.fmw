FME workspace 004_BEW_Eigenaars.fmw
Title: 004_BEW_Eigenaars.fmw
Description: Bewerkingen: 
Berekening van inwonende eigenaars en eigenaarswoningen door vergelijking van adressen wooneenheden en eigenaarsadres(sen).
History: 2016-10-06,Jonas Verstraete,Initial version,2016-10-21,Jonas Verstraete,Update to new cadastre datastructure

Parameters:
- SourceDataset_FFS_9 = ..\data\intermediate\001\001_BevReg_adr_notCRAB.ffs   # Source FME Feature Store (FFS) File(s)
- MINX =   # Minimum X
- MINY =   # Minimum Y
- MAXX =   # Maximum X
- MAXY =   # Maximum Y
- SourceDataset_FFS_14 = ..\data\intermediate\001\001_BevReg_CRAB.ffs   # Source FME Feature Store (FFS) File(s)
- municipality = GENT   # Municipality
- language = nl   # Municipality language
- SourceDataset_FFS_13 = ..\data\intermediate\000\000_CRAB_alladr.ffs   # Source FME Feature Store (FFS) File(s)
- DestDataset_FFS_2 = ..\data\intermediate\004\004_KAD_owner.ffs   # Destination FME Feature Store (FFS) File
- DestDataset_FFS_3 = ..\data\intermediate\004\004_Gebouweenheden_Adressen.ffs   # Destination FME Feature Store (FFS) File
- DestDataset_FFS = ..\data\intermediate\004\004_KAD_percelen.ffs   # Destination FME Feature Store (FFS) File
- SourceDataset_FFS = ..\data\intermediate\003\003_KADparcel_Gebouweenheden.ffs   # Source FME Feature Store (FFS) File(s)
- SourceDataset_FFS_12 = ..\data\intermediate\000\000_KAD.ffs   # Source FME Feature Store (FFS) File(s)
- SourceDataset_FFS_4 = ..\data\intermediate\003\003_Gebouweenheden_Adressen.ffs   # Source FME Feature Store (FFS) File(s)

Readers:
- FFS_1: FFS from $(SourceDataset_FFS_9)
- FFS_2: FFS from $(SourceDataset_FFS_14)
- FFS_3: FFS from $(SourceDataset_FFS_13)
- FFS_4: FFS from $(SourceDataset_FFS)
- FFS_5: FFS from $(SourceDataset_FFS_12)
- FFS_6: FFS from $(SourceDataset_FFS_4)

Writers:
- FFS_7: FFS to $(DestDataset_FFS_2)
- FFS_8: FFS to $(DestDataset_FFS_3)
- FFS_9: FFS to $(DestDataset_FFS)

Note: 004_BEW_Eigenaars.fmw / Bewerkingen: / Berekening van inwonende eigenaars en eigenaarswoningen door vergelijking van adressen wooneenheden en eigenaarsadres(sen).
AttributeCreator_4
    ATTR_TABLE:
      SET_TO municipality = FME_CONDITIONAL:DEFAULT_VALUE'_FME_NO_OP_'BOOL_OP;OR;COMPOSITE_TEST;<Unused>;TEST $(language) = fr'@Value(municipality_fr)'BOOL_OP;OR;COMPOSITE_TEST;<Unused>;TEST $(language) = nl'@Value(municipality_nl)'FME_NUM_CONDITIONS3___
      SET_TO street = FME_CONDITIONAL:DEFAULT_VALUE'_FME_NO_OP_'BOOL_OP;OR;COMPOSITE_TEST;<Unused>;TEST $(language) = fr'@Value(street_fr)'BOOL_OP;OR;COMPOSITE_TEST;<Unused>;TEST $(language) = nl'@Value(street_nl)'FME_NUM_CONDITIONS3___
    -> TestFilter
Note: Gemeente
TestFilter
    DEFAULT_VALUE = <UNFILTERED>
    TEST_LIST = BOOL_OP,AND,COMPOSITE_TEST,<Unused>,TEST_CLAUSE,"TEST @Value(municipality) = $(municipality)",Gemeente
    Gemeente -> StringSearcher
    <UNFILTERED> -> Junction
AttributeKeeper
    KEEP_ATTRS = HUISNR,SUBADRES,GEMNM,INDEX,NUMMER,CRABadrID,STRAATNM
    -> FeatureMerger [SUPPLIER]
Note: Add CRAB adres to KAD adres
FeatureMerger
    JOIN_KEYS = @Value(street) @Value(STRAATNM) AUTO @Value(number) @Value(NUMMER) AUTO @Value(boxNumber) @Value(INDEX) AUTO
    MERGE_TYPE = Attributes Only
    IGNORE_NULLS = No
    SUPPLIERS_FIRST = No
    GEOM_TYPE = Build Polygons
    ATTR_CONFLICT_RES = Use Requestor
    ATTR_ACCUM_MODE = Merge Supplier
    REJECT_NULL_MISSING_KEYS = No
    CONNECT_Z_MODE = First Wins
    PROCESS_DUPS = Yes
    MERGED -> TestFilter_5
    MERGED -> Junction
    NOT_MERGED -> TestFilter_2 [off]
    NOT_MERGED -> StringSearcher_2
StringSearcher_4
    REGEXP = ^[0-9]+$
    STRING_TO_SEARCH = @Value(SUBADRES)
    CASE = no
    MATCHED_RESULT_ATTR = _matched_characters
    MATCHED_PARTS_ATTR = _matched_parts
    MATCHED -> StringFormatter_2
    NOT_MATCHED -> FeatureMerger_2 [SUPPLIER]
StringFormatter_2
    SRC_ATTRS = SUBADRES
    FORMAT = 04s
    -> FeatureMerger_2 [SUPPLIER]
Note: Add CRAB adr die niet in BevReg / wel in KAD_owners / >> niet natuurlijke personen / of inconsistentie tussen BevReg en KAD
FeatureMerger_2
    JOIN_KEYS = @Value(street) @Value(STRAATNM) AUTO @Value(HUISNR) @Value(HUISNR) AUTO @Value(SUBADR) @Value(SUBADRES) AUTO
    MERGE_TYPE = Attributes Only
    IGNORE_NULLS = No
    SUPPLIERS_FIRST = No
    GEOM_TYPE = Build Polygons
    ATTR_CONFLICT_RES = Use Requestor
    ATTR_ACCUM_MODE = Merge Supplier
    REJECT_NULL_MISSING_KEYS = No
    CONNECT_Z_MODE = First Wins
    PROCESS_DUPS = Yes
    MERGED -> TestFilter_5
    MERGED -> Junction
    NOT_MERGED -> Junction
Junction
    -> 004_KAD_owner (writer FFS_7)
004_KAD_owner (writer FFS_7)
    attributes: propertySituationIdf varchar(9), order varchar(3), partyType varchar(3), right varchar(51), right_trad varchar(51), managedBy number(2,0), officialId varchar(12), name varchar(80), firstname varchar(12), birthdate varchar(11), country varchar(3), zipCode varchar(4), municipality_fr varchar(30), municipality_nl varchar(30), street_fr varchar(30), street_nl varchar(30), number varchar(5), boxNumber varchar(5), officialId_partner varchar(13), name_partner varchar(23), firstName_partner varchar(13), birthdate_partner varchar(11), country_partner varchar(3), zipCode_partner varchar(5), municipality_partner_fr varchar(30), municipality_partner_nl varchar(30), street_partner_fr varchar(30), street_partner_nl varchar(30), number_partner varchar(20), boxNumber_partner varchar(5),
      coOwner varchar(16), anonymousOwner varchar(1), dateSituation varchar(9), CRABadrID varchar(10)
Note: Natuurlijke personen
TestFilter_5
    DEFAULT_VALUE = <UNFILTERED>
    TEST_LIST = BOOL_OP,AND,COMPOSITE_TEST,<Unused>,TEST_CLAUSE,"TEST birthdate NOT_ATTRIBUTE_IS_EMPTY """"",Nat pers
    Nat pers -> ListBuilder
ListBuilder
    LIST_NAME = _kadownersList
    GRP_BY = CRABadrID
    -> InlineQuerier_2 [Supplier]
GeometryExtractor
    REMOVE_GEOMETRY = No
    OGC_WKT_PRECISION_DISPLAY = Shortened 64-bit
    KIND_LONG = OGC Well Known Text
    ATTR = _geometry
    OGCVERSION = 1.1
    -> InlineQuerier_2 [Requestor]
Note: Add _KADownersList / to Gebouweenheden / obv eigenaarsadres
InlineQuerier_2
    QUERY_DEF:
      LeftJoin,SELECT *
      FROM Requestor Left join Supplier
      On Requestor."CRABadrID"= Supplier."CRABadrID",FIRST
    QUERY_SCHEMA = LeftJoin,TypeEenh,varchar(60),Functie,varchar(60),Domicilie,varchar(60),CRABadrID,varchar(10),capakey,varchar(17),ParticHh,integer,EenprsHh,integer,MeerprsHh,integer,GemeensHh,integer,HandelID,varchar(10),_huishoudList{}.HuishType,varchar(60),_huishoudList{}.HuishGrootte,integer,_huishoudList{}.GEBDAT,varchar(11),_huishoudList{}.GESLACHT,varchar(2),_huishoudList{}.NATIONALITEIT,integer,_huishoudList{}.VERWERVING,integer,_huishoudList{}.REFPERS,varchar(2),_huishoudList{}.GEZINSGROOTTE,integer,_huishoudList{}.AANTKIND,integer,_huishoudList{}.BURGSTAAT,varchar(15),_huishoudList{}.NAT_OUD,integer,_huishoudList{}.REGISTER,varchar(6),_huishoudList{}.BevRegID,varchar(10),STRAATNM,varchar(255),HUISNR,varchar(10),SUBADRES,varchar(255),PKANCODE,integer,GEMNM,varchar(4),Gebouweenh,integer,Wooneenh,integer,GebouwType,varchar(150),_inwList{}.STRAATKODE,varchar(8),_inwList{}.NUMMER,varchar(5),_inwList{}.INDEX,varchar(5),_inwList{}.GEBDAT,varchar(11),_inwList{}.GESLACHT,varchar(2),_inwList{}.NATIONALITEIT,integer,_inwList{}.VERWERVING,integer,_inwList{}.REFPERS,varchar(2),_inwList{}.GEZINSGROOTTE,integer,_inwList{}.AANTKIND,integer,_inwList{}.BURGSTAAT,varchar(15),_inwList{}.NAT_OUD,integer,_inwList{}.REGISTER,varchar(6),_inwList{}.sector,varchar(5),_inwList{}.stadsdeel,varchar(16),_inwList{}.wijknaam,varchar(30),_inwList{}.gemeensch,varchar(12),_inwList{}.BevRegID,varchar(10),_inwList{}.CRAB_merge,varchar(254),_inwList{}.CRABadrID,varchar(10),_inwList{}.GEMNM,varchar(4),_inwList{}.PKANCODE,integer,_geometry,varchar(200),Requestor.fme_feature_content,fme_feature_content,_kadownersList{}.propertySituationIdf,varchar(200),_kadownersList{}.order,varchar(200),_kadownersList{}.partyType,varchar(200),_kadownersList{}.right,varchar(200),_kadownersList{}.right_trad,varchar(200),_kadownersList{}.managedBy,varchar(200),_kadownersList{}.officialId,varchar(200),_kadownersList{}.name,varchar(200),_kadownersList{}.firstname,varchar(200),_kadownersList{}.birthdate,varchar(200),_kadownersList{}.country,varchar(200),_kadownersList{}.zipCode,varchar(200),_kadownersList{}.municipality_fr,varchar(200),_kadownersList{}.municipality_nl,varchar(200),_kadownersList{}.municipality,varchar(200),_kadownersList{}.street,varchar(200),_kadownersList{}.street_fr,varchar(200),_kadownersList{}.street_nl,varchar(200),_kadownersList{}.number,varchar(200),_kadownersList{}.boxNumber,varchar(200),_kadownersList{}.officialId_partner,varchar(200),_kadownersList{}.name_partner,varchar(200),_kadownersList{}.firstName_partner,varchar(200),_kadownersList{}.birthdate_partner,varchar(200),_kadownersList{}.country_partner,varchar(200),_kadownersList{}.zipCode_partner,varchar(200),_kadownersList{}.municipality_partner_fr,varchar(200),_kadownersList{}.municipality_partner_nl,varchar(200),_kadownersList{}.street_partner_fr,varchar(200),_kadownersList{}.street_partner_nl,varchar(200),_kadownersList{}.number_partner,varchar(200),_kadownersList{}.boxNumber_partner,varchar(200),_kadownersList{}.coOwner,varchar(200),_kadownersList{}.anonymousOwner,varchar(200),_kadownersList{}.dateSituation,varchar(200),_kadownersList{}.NUMMER,varchar(200),_kadownersList{}.INDEX,varchar(200),_kadownersList{}.CRABadrID,varchar(200),_kadownersList{}.GEMNM,varchar(200),_kadownersList{}.HUISNR,varchar(200),_kadownersList{}.STRAATNM,varchar(200),_kadownersList{}.SUBADRES,varchar(200),_kadownersList{}.SUBADR,varchar(200),_kadownersList{}.POSTKODE,varchar(200),_kadownersList{}.STRAATKODE,varchar(200),_kadownersList{}.sector,varchar(200),_kadownersList{}.stadsdeel,varchar(200),_kadownersList{}.wijknaam,varchar(200),_kadownersList{}.CRAB_merge,varchar(200),_kadownersList{}.PKANCODE,varchar(200),_kadownersList{}.adrType,varchar(200),_kadownersList{}.STRAATNMID,varchar(200),_kadownersList{}.HUISNRID,varchar(200),_kadownersList{}.HUISNR_BEG,varchar(200),_kadownersList{}.HUISNR_TIJ,varchar(200),_kadownersList{}.HUISNR_EIN,varchar(200),_kadownersList{}.SUBADRESID,varchar(200),_kadownersList{}.SUBADR_BEG,varchar(200),_kadownersList{}.AARDSUBADR,varchar(200),_kadownersList{}.NISGEMCODE,varchar(200),_kadownersList{}.AARDADRPOS,varchar(200),_kadownersList{}.X,varchar(200),_kadownersList{}.Y,varchar(200),_kadownersList{}.SUBADR_TIJ,varchar(200),_kadownersList{}.SUBADR_EIN,varchar(200),_kadownersList{}._matched_characters,varchar(200),_kadownersList{}._matched_parts{},varchar(200),Supplier.fme_feature_content,fme_feature_content
    TABLE_DEF = Requestor,TypeEenh,varchar(60),Functie,varchar(60),Domicilie,varchar(60),CRABadrID,varchar(10),capakey,varchar(17),ParticHh,integer,EenprsHh,integer,MeerprsHh,integer,GemeensHh,integer,HandelID,varchar(10),_huishoudList{}.HuishType,varchar(60),_huishoudList{}.HuishGrootte,integer,_huishoudList{}.GEBDAT,varchar(11),_huishoudList{}.GESLACHT,varchar(2),_huishoudList{}.NATIONALITEIT,integer,_huishoudList{}.VERWERVING,integer,_huishoudList{}.REFPERS,varchar(2),_huishoudList{}.GEZINSGROOTTE,integer,_huishoudList{}.AANTKIND,integer,_huishoudList{}.BURGSTAAT,varchar(15),_huishoudList{}.NAT_OUD,integer,_huishoudList{}.REGISTER,varchar(6),_huishoudList{}.BevRegID,varchar(10),STRAATNM,varchar(255),HUISNR,varchar(10),SUBADRES,varchar(255),PKANCODE,integer,GEMNM,varchar(4),Gebouweenh,integer,Wooneenh,integer,GebouwType,varchar(150),_inwList{}.STRAATKODE,varchar(8),_inwList{}.NUMMER,varchar(5),_inwList{}.INDEX,varchar(5),_inwList{}.GEBDAT,varchar(11),_inwList{}.GESLACHT,varchar(2),_inwList{}.NATIONALITEIT,integer,_inwList{}.VERWERVING,integer,_inwList{}.REFPERS,varchar(2),_inwList{}.GEZINSGROOTTE,integer,_inwList{}.AANTKIND,integer,_inwList{}.BURGSTAAT,varchar(15),_inwList{}.NAT_OUD,integer,_inwList{}.REGISTER,varchar(6),_inwList{}.sector,varchar(5),_inwList{}.stadsdeel,varchar(16),_inwList{}.wijknaam,varchar(30),_inwList{}.gemeensch,varchar(12),_inwList{}.BevRegID,varchar(10),_inwList{}.CRAB_merge,varchar(254),_inwList{}.CRABadrID,varchar(10),_inwList{}.GEMNM,varchar(4),_inwList{}.PKANCODE,integer,_geometry,varchar(200),Supplier,CRABadrID,varchar(10),_kadownersList{}.propertySituationIdf,varchar(200),_kadownersList{}.order,varchar(200),_kadownersList{}.partyType,varchar(200),_kadownersList{}.right,varchar(200),_kadownersList{}.right_trad,varchar(200),_kadownersList{}.managedBy,varchar(200),_kadownersList{}.officialId,varchar(200),_kadownersList{}.name,varchar(200),_kadownersList{}.firstname,varchar(200),_kadownersList{}.birthdate,varchar(200),_kadownersList{}.country,varchar(200),_kadownersList{}.zipCode,varchar(200),_kadownersList{}.municipality_fr,varchar(200),_kadownersList{}.municipality_nl,varchar(200),_kadownersList{}.municipality,varchar(200),_kadownersList{}.street,varchar(200),_kadownersList{}.street_fr,varchar(200),_kadownersList{}.street_nl,varchar(200),_kadownersList{}.number,varchar(200),_kadownersList{}.boxNumber,varchar(200),_kadownersList{}.officialId_partner,varchar(200),_kadownersList{}.name_partner,varchar(200),_kadownersList{}.firstName_partner,varchar(200),_kadownersList{}.birthdate_partner,varchar(200),_kadownersList{}.country_partner,varchar(200),_kadownersList{}.zipCode_partner,varchar(200),_kadownersList{}.municipality_partner_fr,varchar(200),_kadownersList{}.municipality_partner_nl,varchar(200),_kadownersList{}.street_partner_fr,varchar(200),_kadownersList{}.street_partner_nl,varchar(200),_kadownersList{}.number_partner,varchar(200),_kadownersList{}.boxNumber_partner,varchar(200),_kadownersList{}.coOwner,varchar(200),_kadownersList{}.anonymousOwner,varchar(200),_kadownersList{}.dateSituation,varchar(200),_kadownersList{}.NUMMER,varchar(200),_kadownersList{}.INDEX,varchar(200),_kadownersList{}.CRABadrID,varchar(200),_kadownersList{}.GEMNM,varchar(200),_kadownersList{}.HUISNR,varchar(200),_kadownersList{}.STRAATNM,varchar(200),_kadownersList{}.SUBADRES,varchar(200),_kadownersList{}.SUBADR,varchar(200),_kadownersList{}.POSTKODE,varchar(200),_kadownersList{}.STRAATKODE,varchar(200),_kadownersList{}.sector,varchar(200),_kadownersList{}.stadsdeel,varchar(200),_kadownersList{}.wijknaam,varchar(200),_kadownersList{}.CRAB_merge,varchar(200),_kadownersList{}.PKANCODE,varchar(200),_kadownersList{}.adrType,varchar(200),_kadownersList{}.STRAATNMID,varchar(200),_kadownersList{}.HUISNRID,varchar(200),_kadownersList{}.HUISNR_BEG,varchar(200),_kadownersList{}.HUISNR_TIJ,varchar(200),_kadownersList{}.HUISNR_EIN,varchar(200),_kadownersList{}.SUBADRESID,varchar(200),_kadownersList{}.SUBADR_BEG,varchar(200),_kadownersList{}.AARDSUBADR,varchar(200),_kadownersList{}.NISGEMCODE,varchar(200),_kadownersList{}.AARDADRPOS,varchar(200),_kadownersList{}.X,varchar(200),_kadownersList{}.Y,varchar(200),_kadownersList{}.SUBADR_TIJ,varchar(200),_kadownersList{}.SUBADR_EIN,varchar(200),_kadownersList{}._matched_characters,varchar(200),_kadownersList{}._matched_parts{},varchar(200)
    LeftJoin -> BulkAttributeRemover_2
BulkAttributeRemover_2
    ATTR_EXP = _kadownersList{}.|_inwList{}.|_huishoudList{}.
    -> InlineQuerier [Requestor]
AttributeKeeper_2
    KEEP_LIST = _kadparcelList{}
    KEEP_ATTRS = capakey
    -> GeometryRemover
GeometryRemover
    -> InlineQuerier [Supplier]
Note: Add _KADparcelList / to Gebouweenheden / obv capakey
InlineQuerier
    QUERY_DEF:
      LeftJoin,SELECT *
      FROM Requestor Left Join Supplier
      On Requestor."capakey" = Supplier."capakey",FIRST
    QUERY_SCHEMA = LeftJoin,TypeEenh,varchar(60),Functie,varchar(60),Domicilie,varchar(60),CRABadrID,varchar(10),capakey,varchar(17),ParticHh,integer,EenprsHh,integer,MeerprsHh,integer,GemeensHh,integer,HandelID,varchar(10),_huishoudList{}.HuishType,varchar(60),_huishoudList{}.HuishGrootte,integer,_huishoudList{}.GEBDAT,varchar(11),_huishoudList{}.GESLACHT,varchar(2),_huishoudList{}.NATIONALITEIT,integer,_huishoudList{}.VERWERVING,integer,_huishoudList{}.REFPERS,varchar(2),_huishoudList{}.GEZINSGROOTTE,integer,_huishoudList{}.AANTKIND,integer,_huishoudList{}.BURGSTAAT,varchar(15),_huishoudList{}.NAT_OUD,integer,_huishoudList{}.REGISTER,varchar(6),_huishoudList{}.BevRegID,varchar(10),STRAATNM,varchar(255),HUISNR,varchar(10),SUBADRES,varchar(255),PKANCODE,integer,GEMNM,varchar(4),Gebouweenh,integer,Wooneenh,integer,GebouwType,varchar(150),_inwList{}.STRAATKODE,varchar(8),_inwList{}.NUMMER,varchar(5),_inwList{}.INDEX,varchar(5),_inwList{}.GEBDAT,varchar(11),_inwList{}.GESLACHT,varchar(2),_inwList{}.NATIONALITEIT,integer,_inwList{}.VERWERVING,integer,_inwList{}.REFPERS,varchar(2),_inwList{}.GEZINSGROOTTE,integer,_inwList{}.AANTKIND,integer,_inwList{}.BURGSTAAT,varchar(15),_inwList{}.NAT_OUD,integer,_inwList{}.REGISTER,varchar(6),_inwList{}.sector,varchar(5),_inwList{}.stadsdeel,varchar(16),_inwList{}.wijknaam,varchar(30),_inwList{}.gemeensch,varchar(12),_inwList{}.BevRegID,varchar(10),_inwList{}.CRAB_merge,varchar(254),_inwList{}.CRABadrID,varchar(10),_inwList{}.GEMNM,varchar(4),_inwList{}.PKANCODE,integer,_geometry,varchar(200),_kadownersList{}.propertySituationIdf,varchar(200),_kadownersList{}.order,varchar(200),_kadownersList{}.partyType,varchar(200),_kadownersList{}.right,varchar(200),_kadownersList{}.right_trad,varchar(200),_kadownersList{}.managedBy,varchar(200),_kadownersList{}.officialId,varchar(200),_kadownersList{}.name,varchar(200),_kadownersList{}.firstname,varchar(200),_kadownersList{}.birthdate,varchar(200),_kadownersList{}.country,varchar(200),_kadownersList{}.zipCode,varchar(200),_kadownersList{}.municipality,varchar(200),_kadownersList{}.municipality_fr,varchar(200),_kadownersList{}.municipality_nl,varchar(200),_kadownersList{}.street,varchar(200),_kadownersList{}.street_fr,varchar(200),_kadownersList{}.street_nl,varchar(200),_kadownersList{}.number,varchar(200),_kadownersList{}.boxNumber,varchar(200),_kadownersList{}.officialId_partner,varchar(200),_kadownersList{}.name_partner,varchar(200),_kadownersList{}.firstName_partner,varchar(200),_kadownersList{}.birthdate_partner,varchar(200),_kadownersList{}.country_partner,varchar(200),_kadownersList{}.zipCode_partner,varchar(200),_kadownersList{}.municipality_partner_fr,varchar(200),_kadownersList{}.municipality_partner_nl,varchar(200),_kadownersList{}.street_partner_fr,varchar(200),_kadownersList{}.street_partner_nl,varchar(200),_kadownersList{}.number_partner,varchar(200),_kadownersList{}.boxNumber_partner,varchar(200),_kadownersList{}.coOwner,varchar(200),_kadownersList{}.anonymousOwner,varchar(200),_kadownersList{}.dateSituation,varchar(200),_kadownersList{}.NUMMER,varchar(200),_kadownersList{}.INDEX,varchar(200),_kadownersList{}.CRABadrID,varchar(200),_kadownersList{}.GEMNM,varchar(200),_kadownersList{}.HUISNR,varchar(200),_kadownersList{}.STRAATNM,varchar(200),_kadownersList{}.SUBADRES,varchar(200),_kadownersList{}.SUBADR,varchar(200),_kadownersList{}.POSTKODE,varchar(200),_kadownersList{}.STRAATKODE,varchar(200),_kadownersList{}.sector,varchar(200),_kadownersList{}.stadsdeel,varchar(200),_kadownersList{}.wijknaam,varchar(200),_kadownersList{}.CRAB_merge,varchar(200),_kadownersList{}.PKANCODE,varchar(200),_kadownersList{}.adrType,varchar(200),_kadownersList{}.STRAATNMID,varchar(200),_kadownersList{}.HUISNRID,varchar(200),_kadownersList{}.HUISNR_BEG,varchar(200),_kadownersList{}.HUISNR_TIJ,varchar(200),_kadownersList{}.HUISNR_EIN,varchar(200),_kadownersList{}.SUBADRESID,varchar(200),_kadownersList{}.SUBADR_BEG,varchar(200),_kadownersList{}.AARDSUBADR,varchar(200),_kadownersList{}.NISGEMCODE,varchar(200),_kadownersList{}.AARDADRPOS,varchar(200),_kadownersList{}.X,varchar(200),_kadownersList{}.Y,varchar(200),_kadownersList{}.SUBADR_TIJ,varchar(200),_kadownersList{}.SUBADR_EIN,varchar(200),_kadownersList{}._matched_characters,varchar(200),_kadownersList{}._matched_parts{},varchar(200),Requestor.fme_feature_content,fme_feature_content,_kadparcelList{}.constructionIndication,integer,_kadparcelList{}.propertySituationIdf,integer,_kadparcelList{}.divCad,integer,_kadparcelList{}.section,varchar(1),_kadparcelList{}.primaryNumber,integer,_kadparcelList{}.bisNumber,integer,_kadparcelList{}.exponentLetter,varchar(1),_kadparcelList{}.exponentNumber,integer,_kadparcelList{}.partNumber,varchar(5),_kadparcelList{}.capakey,varchar(17),_kadparcelList{}.order,varchar(4),_kadparcelList{}.nature,varchar(3),_kadparcelList{}.descriptPrivate,varchar(35),_kadparcelList{}.block,varchar(2),_kadparcelList{}.floor,varchar(2),_kadparcelList{}.floorSituation,varchar(5),_kadparcelList{}.crossDetail,varchar(20),_kadparcelList{}.matUtil,varchar(1),_kadparcelList{}.notTaxedMatUtil,varchar(3),_kadparcelList{}.nisCom,varchar(6),_kadparcelList{}.street_situation,varchar(20),_kadparcelList{}.street_translation,varchar(1),_kadparcelList{}.street_code,varchar(6),_kadparcelList{}.number,varchar(6),_kadparcelList{}.polWa,varchar(8),_kadparcelList{}.surfaceNotTaxable,integer,_kadparcelList{}.surfaceTaxable,integer,_kadparcelList{}.surfaceVerif,varchar(2),_kadparcelList{}.constructionYear,integer,_kadparcelList{}.soilIndex,integer,_kadparcelList{}.soilRent,varchar(2),_kadparcelList{}.cadastralIncomePerSurface,integer,_kadparcelList{}.cadastralIncomePerSurfaceOtherDi,integer,_kadparcelList{}.numberCadastralIncome,integer,_kadparcelList{}.charCadastralIncome,varchar(1),_kadparcelList{}.cadastralIncome,integer,_kadparcelList{}.dateEndExoneration,varchar(1),_kadparcelList{}.decrete,varchar(1),_kadparcelList{}.constructionType,varchar(2),_kadparcelList{}.floorNumberAboveground,integer,_kadparcelList{}.garret,integer,_kadparcelList{}.physModYear,integer,_kadparcelList{}.constructionQuality,varchar(2),_kadparcelList{}.garageNumber,integer,_kadparcelList{}.centralHeating,integer,_kadparcelList{}.bathroomNumber,integer,_kadparcelList{}.housingUnitNumber,integer,_kadparcelList{}.placeNumber,integer,_kadparcelList{}.builtSurface,integer,_kadparcelList{}.usedSurface,integer,_kadparcelList{}.dateSituation,varchar(200),_kadparcelList{}.aard,varchar(10),_kadparcelList{}.bouwjaar,varchar(25),_kadparcelList{}.GebouwType,varchar(200),Supplier.fme_feature_content,fme_feature_content
    TABLE_DEF = Requestor,TypeEenh,varchar(60),Functie,varchar(60),Domicilie,varchar(60),CRABadrID,varchar(10),capakey,varchar(17),ParticHh,integer,EenprsHh,integer,MeerprsHh,integer,GemeensHh,integer,HandelID,varchar(10),_huishoudList{}.HuishType,varchar(60),_huishoudList{}.HuishGrootte,integer,_huishoudList{}.GEBDAT,varchar(11),_huishoudList{}.GESLACHT,varchar(2),_huishoudList{}.NATIONALITEIT,integer,_huishoudList{}.VERWERVING,integer,_huishoudList{}.REFPERS,varchar(2),_huishoudList{}.GEZINSGROOTTE,integer,_huishoudList{}.AANTKIND,integer,_huishoudList{}.BURGSTAAT,varchar(15),_huishoudList{}.NAT_OUD,integer,_huishoudList{}.REGISTER,varchar(6),_huishoudList{}.BevRegID,varchar(10),STRAATNM,varchar(255),HUISNR,varchar(10),SUBADRES,varchar(255),PKANCODE,integer,GEMNM,varchar(4),Gebouweenh,integer,Wooneenh,integer,GebouwType,varchar(150),_inwList{}.STRAATKODE,varchar(8),_inwList{}.NUMMER,varchar(5),_inwList{}.INDEX,varchar(5),_inwList{}.GEBDAT,varchar(11),_inwList{}.GESLACHT,varchar(2),_inwList{}.NATIONALITEIT,integer,_inwList{}.VERWERVING,integer,_inwList{}.REFPERS,varchar(2),_inwList{}.GEZINSGROOTTE,integer,_inwList{}.AANTKIND,integer,_inwList{}.BURGSTAAT,varchar(15),_inwList{}.NAT_OUD,integer,_inwList{}.REGISTER,varchar(6),_inwList{}.sector,varchar(5),_inwList{}.stadsdeel,varchar(16),_inwList{}.wijknaam,varchar(30),_inwList{}.gemeensch,varchar(12),_inwList{}.BevRegID,varchar(10),_inwList{}.CRAB_merge,varchar(254),_inwList{}.CRABadrID,varchar(10),_inwList{}.GEMNM,varchar(4),_inwList{}.PKANCODE,integer,_geometry,varchar(200),_kadownersList{}.propertySituationIdf,varchar(200),_kadownersList{}.order,varchar(200),_kadownersList{}.partyType,varchar(200),_kadownersList{}.right,varchar(200),_kadownersList{}.right_trad,varchar(200),_kadownersList{}.managedBy,varchar(200),_kadownersList{}.officialId,varchar(200),_kadownersList{}.name,varchar(200),_kadownersList{}.firstname,varchar(200),_kadownersList{}.birthdate,varchar(200),_kadownersList{}.country,varchar(200),_kadownersList{}.zipCode,varchar(200),_kadownersList{}.municipality,varchar(200),_kadownersList{}.municipality_fr,varchar(200),_kadownersList{}.municipality_nl,varchar(200),_kadownersList{}.street,varchar(200),_kadownersList{}.street_fr,varchar(200),_kadownersList{}.street_nl,varchar(200),_kadownersList{}.number,varchar(200),_kadownersList{}.boxNumber,varchar(200),_kadownersList{}.officialId_partner,varchar(200),_kadownersList{}.name_partner,varchar(200),_kadownersList{}.firstName_partner,varchar(200),_kadownersList{}.birthdate_partner,varchar(200),_kadownersList{}.country_partner,varchar(200),_kadownersList{}.zipCode_partner,varchar(200),_kadownersList{}.municipality_partner_fr,varchar(200),_kadownersList{}.municipality_partner_nl,varchar(200),_kadownersList{}.street_partner_fr,varchar(200),_kadownersList{}.street_partner_nl,varchar(200),_kadownersList{}.number_partner,varchar(200),_kadownersList{}.boxNumber_partner,varchar(200),_kadownersList{}.coOwner,varchar(200),_kadownersList{}.anonymousOwner,varchar(200),_kadownersList{}.dateSituation,varchar(200),_kadownersList{}.NUMMER,varchar(200),_kadownersList{}.INDEX,varchar(200),_kadownersList{}.CRABadrID,varchar(200),_kadownersList{}.GEMNM,varchar(200),_kadownersList{}.HUISNR,varchar(200),_kadownersList{}.STRAATNM,varchar(200),_kadownersList{}.SUBADRES,varchar(200),_kadownersList{}.SUBADR,varchar(200),_kadownersList{}.POSTKODE,varchar(200),_kadownersList{}.STRAATKODE,varchar(200),_kadownersList{}.sector,varchar(200),_kadownersList{}.stadsdeel,varchar(200),_kadownersList{}.wijknaam,varchar(200),_kadownersList{}.CRAB_merge,varchar(200),_kadownersList{}.PKANCODE,varchar(200),_kadownersList{}.adrType,varchar(200),_kadownersList{}.STRAATNMID,varchar(200),_kadownersList{}.HUISNRID,varchar(200),_kadownersList{}.HUISNR_BEG,varchar(200),_kadownersList{}.HUISNR_TIJ,varchar(200),_kadownersList{}.HUISNR_EIN,varchar(200),_kadownersList{}.SUBADRESID,varchar(200),_kadownersList{}.SUBADR_BEG,varchar(200),_kadownersList{}.AARDSUBADR,varchar(200),_kadownersList{}.NISGEMCODE,varchar(200),_kadownersList{}.AARDADRPOS,varchar(200),_kadownersList{}.X,varchar(200),_kadownersList{}.Y,varchar(200),_kadownersList{}.SUBADR_TIJ,varchar(200),_kadownersList{}.SUBADR_EIN,varchar(200),_kadownersList{}._matched_characters,varchar(200),_kadownersList{}._matched_parts{},varchar(200),Supplier,capakey,varchar(17),_kadparcelList{}.constructionIndication,integer,_kadparcelList{}.propertySituationIdf,integer,_kadparcelList{}.divCad,integer,_kadparcelList{}.section,varchar(1),_kadparcelList{}.primaryNumber,integer,_kadparcelList{}.bisNumber,integer,_kadparcelList{}.exponentLetter,varchar(1),_kadparcelList{}.exponentNumber,integer,_kadparcelList{}.partNumber,varchar(5),_kadparcelList{}.capakey,varchar(17),_kadparcelList{}.order,varchar(4),_kadparcelList{}.nature,varchar(3),_kadparcelList{}.descriptPrivate,varchar(35),_kadparcelList{}.block,varchar(2),_kadparcelList{}.floor,varchar(2),_kadparcelList{}.floorSituation,varchar(5),_kadparcelList{}.crossDetail,varchar(20),_kadparcelList{}.matUtil,varchar(1),_kadparcelList{}.notTaxedMatUtil,varchar(3),_kadparcelList{}.nisCom,varchar(6),_kadparcelList{}.street_situation,varchar(20),_kadparcelList{}.street_translation,varchar(1),_kadparcelList{}.street_code,varchar(6),_kadparcelList{}.number,varchar(6),_kadparcelList{}.polWa,varchar(8),_kadparcelList{}.surfaceNotTaxable,integer,_kadparcelList{}.surfaceTaxable,integer,_kadparcelList{}.surfaceVerif,varchar(2),_kadparcelList{}.constructionYear,integer,_kadparcelList{}.soilIndex,integer,_kadparcelList{}.soilRent,varchar(2),_kadparcelList{}.cadastralIncomePerSurface,integer,_kadparcelList{}.cadastralIncomePerSurfaceOtherDi,integer,_kadparcelList{}.numberCadastralIncome,integer,_kadparcelList{}.charCadastralIncome,varchar(1),_kadparcelList{}.cadastralIncome,integer,_kadparcelList{}.dateEndExoneration,varchar(1),_kadparcelList{}.decrete,varchar(1),_kadparcelList{}.constructionType,varchar(2),_kadparcelList{}.floorNumberAboveground,integer,_kadparcelList{}.garret,integer,_kadparcelList{}.physModYear,integer,_kadparcelList{}.constructionQuality,varchar(2),_kadparcelList{}.garageNumber,integer,_kadparcelList{}.centralHeating,integer,_kadparcelList{}.bathroomNumber,integer,_kadparcelList{}.housingUnitNumber,integer,_kadparcelList{}.placeNumber,integer,_kadparcelList{}.builtSurface,integer,_kadparcelList{}.usedSurface,integer,_kadparcelList{}.dateSituation,varchar(200),_kadparcelList{}.aard,varchar(10),_kadparcelList{}.bouwjaar,varchar(25),_kadparcelList{}.GebouwType,varchar(200)
    LeftJoin -> GeometryReplacer
GeometryReplacer
    KIND_LONG = OGC Well Known Text
    SOURCE = @Value(_geometry)
    OGC_WKT_PRECISION_DISPLAY = 64-bit
    REMOVE_ATTRIBUTE = Yes
    -> BulkAttributeRemover_3
BulkAttributeRemover_3
    ATTR_EXP = _kadownersList{}.|_inwList{}.|_huishoudList{}.|_kadparcelList{}.
    -> TestFilter_6
TestFilter_6
    DEFAULT_VALUE = <UNFILTERED>
    TEST_LIST:
      BOOL_OP,OR,COMPOSITE_TEST,<Unused>,TEST_CLAUSE,"TEST _kadownersList{0}.propertySituationIdf ATTRIBUTE_IS_MISSING """"
      TEST _kadparcelList{0}.propertySituationIdf ATTRIBUTE_IS_MISSING """"",List missing
    List missing -> PassThrough
    <UNFILTERED> -> AttributeExposer_2
AttributeExposer_2
    ATTR_LIST = _kadparcelList{}.propertySituationIdf,_kadownersList{}.propertySituationIdf
    -> ListComparer_2
Note: Check of eigenaars wonend in gebouweenheid / eigenaar zijn van een eigendom op het onderliggende perceel.
Note: Geen rechtstreekse koppeling Gebouweenheden en KAD eigendommen. / >> Onbekend: welke zijn de eigenaars van een gebouweenheid. / >> Wel gekend: welke zijn de eigenaars van de KAD eigendommen op het onderliggende perceel. / >> Wel gekend: welke eigenaars van een eigendom in Gent wonen in welke gebouweenheid. / >> Wel gekend: welke eigenaars wonen in hun eigen eigendom. / (eigenlijk: welke eigenaars wonen in een gebouweenheid op een perceel waar hij/zij ook één of meerderre eigendommen heeft. ) / Mogelijke uitzondering: / Persoon die niet in eigen eigendom woont maar wel een eigendom op hetzelfde perceel bezit >> toch als inwonende eigenaar beschouwd
ListComparer_2
    SECOND_LIST_ATTR = _kadparcelList{}.propertySituationIdf
    LIST_NAME_ONLYFIRST = _onlyfirst
    LIST_NAME_BOTHSECOND = _inwParcelList
    FIRST_LIST_ATTR = _kadownersList{}.propertySituationIdf
    LIST_NAME_ONLYSECOND = _onlysecond
    MODE = MANYtoONE
    LIST_NAME_BOTHFIRST = _inwOwnerList
    -> ListCopier
ListCopier
    SRC_LIST = _inwOwnerList{}
    DEST_LIST = _inwEigenaarsList
    -> AttributeExposer
AttributeExposer
    ATTR_LIST = _inwEigenaarsList{}.officialId
    -> ListDuplicateRemover
ListDuplicateRemover
    SRC_LIST = _inwEigenaarsList{}.officialId
    -> ListElementCounter
ListElementCounter
    CNT_ATTR = InwEigenaars
    LIST_NAME = _inwEigenaarsList{}
    -> TestFilter_3
TestFilter_3
    DEFAULT_VALUE = <UNFILTERED>
    TEST_LIST = BOOL_OP,OR,COMPOSITE_TEST,<Unused>,TEST_CLAUSE,"TEST @Value(InwEigenaars) > 0",Eigenaarswoning
    Eigenaarswoning -> AttributeCreator_2
    <UNFILTERED> -> AttributeRemover_4
AttributeCreator_2
    ATTR_TABLE = SET_TO EigWoning = Eigenaarswoning
    -> PassThrough
AttributeRemover_4
    REMOVE_ATTRS = InwEigenaars
    -> PassThrough
PassThrough: Tester
    TEST_DESCRIPTION = ""
    TEST_CLAUSE = TEST 0 = 0
    BOOL_OP = OR
    TEST_MODE = Automatic
    PASSED -> 004_Gebouweenheden_Adressen (writer FFS_8)
    PASSED -> AttributeRemover_2
004_Gebouweenheden_Adressen (writer FFS_8)
    attributes: TypeEenh varchar(60), Functie varchar(60), Domicilie varchar(60), CRABadrID varchar(10), capakey varchar(17), ParticHh number(3,0), EenprsHh number(3,0), MeerprsHh number(3,0), GemeensHh number(3,0), HandelID varchar(10), _huishoudList{}.HuishType varchar(60), _huishoudList{}.HuishGrootte number(3,0), _huishoudList{}.GEBDAT varchar(11), _huishoudList{}.GESLACHT varchar(2), _huishoudList{}.NATIONALITEIT number(4,0), _huishoudList{}.VERWERVING number(3,0), _huishoudList{}.REFPERS varchar(2), _huishoudList{}.GEZINSGROOTTE number(3,0), _huishoudList{}.AANTKIND number(3,0), _huishoudList{}.BURGSTAAT varchar(15), _huishoudList{}.NAT_OUD number(4,0), _huishoudList{}.REGISTER varchar(6), _huishoudList{}.BevRegID varchar(10), STRAATNM varchar(255), HUISNR varchar(10), SUBADRES varchar(255), PKANCODE number(11,0), GEMNM varchar(4), Gebouweenh number(3,0), Wooneenh number(3,0),
      GebouwType varchar(150), _inwList{}.STRAATKODE varchar(8), _inwList{}.NUMMER varchar(5), _inwList{}.INDEX varchar(5), _inwList{}.GEBDAT varchar(11), _inwList{}.GESLACHT varchar(2), _inwList{}.NATIONALITEIT number(4,0), _inwList{}.VERWERVING number(3,0), _inwList{}.REFPERS varchar(2), _inwList{}.GEZINSGROOTTE number(3,0), _inwList{}.AANTKIND number(3,0), _inwList{}.BURGSTAAT varchar(15), _inwList{}.NAT_OUD number(4,0), _inwList{}.REGISTER varchar(6), _inwList{}.sector varchar(5), _inwList{}.stadsdeel varchar(16), _inwList{}.wijknaam varchar(30), _inwList{}.gemeensch varchar(12), _inwList{}.BevRegID varchar(10), _inwList{}.CRAB_merge varchar(254), _inwList{}.CRABadrID varchar(10), _inwList{}.GEMNM varchar(4), _inwList{}.PKANCODE number(11,0), EigWoning varchar(30), InwEigenaars number(4,0), _inwEigenaarsList{}.officialId varchar(12), _inwEigenaarsList{}.name varchar(80), _inwEigenaarsList{}.firstname varchar(12), _inwEigenaarsList{}.birthdate varchar(11), _inwEigenaarsList{}.country varchar(3),
      _inwEigenaarsList{}.zipCode varchar(4), _inwEigenaarsList{}.municipality_fr varchar(30), _inwEigenaarsList{}.municipality_nl varchar(30), _inwEigenaarsList{}.street_fr varchar(30), _inwEigenaarsList{}.street_nl varchar(30), _inwEigenaarsList{}.number varchar(5), _inwEigenaarsList{}.boxNumber varchar(5), _inwEigenaarsList{}.officialId_partner varchar(13), _inwEigenaarsList{}.name_partner varchar(23), _inwEigenaarsList{}.firstName_partner varchar(13), _inwEigenaarsList{}.birthdate_partner varchar(11), _inwEigenaarsList{}.country_partner varchar(3), _inwEigenaarsList{}.zipCode_partner varchar(5), _inwEigenaarsList{}.municipality_partner_fr varchar(30), _inwEigenaarsList{}.municipality_partner_nl varchar(30), _inwEigenaarsList{}.street_partner_fr varchar(30), _inwEigenaarsList{}.street_partner_nl varchar(30), _inwEigenaarsList{}.number_partner varchar(20), _inwEigenaarsList{}.boxNumber_partner varchar(5), _inwEigenaarsList{}.coOwner varchar(16), _inwEigenaarsList{}.anonymousOwner varchar(1), _inwEigenaarsList{}.CRABadrID varchar(10), _inwOwnerList{}.propertySituationIdf varchar(9), _inwOwnerList{}.order varchar(3), _inwOwnerList{}.partyType varchar(3), _inwOwnerList{}.right varchar(51), _inwOwnerList{}.right_trad varchar(51), _inwOwnerList{}.managedBy number(2,0), _inwOwnerList{}.officialId varchar(12), _inwOwnerList{}.name varchar(80),
      _inwOwnerList{}.firstname varchar(12), _inwOwnerList{}.birthdate varchar(11), _inwOwnerList{}.country varchar(3), _inwOwnerList{}.zipCode varchar(4), _inwOwnerList{}.municipality_fr varchar(30), _inwOwnerList{}.municipality_nl varchar(30), _inwOwnerList{}.street_fr varchar(30), _inwOwnerList{}.street_nl varchar(30), _inwOwnerList{}.number varchar(5), _inwOwnerList{}.boxNumber varchar(5), _inwOwnerList{}.officialId_partner varchar(13), _inwOwnerList{}.name_partner varchar(23), _inwOwnerList{}.firstName_partner varchar(13), _inwOwnerList{}.birthdate_partner varchar(11), _inwOwnerList{}.country_partner varchar(3), _inwOwnerList{}.zipCode_partner varchar(5), _inwOwnerList{}.municipality_partner_fr varchar(30), _inwOwnerList{}.municipality_partner_nl varchar(30), _inwOwnerList{}.street_partner_fr varchar(30), _inwOwnerList{}.street_partner_nl varchar(30), _inwOwnerList{}.number_partner varchar(20), _inwOwnerList{}.boxNumber_partner varchar(5), _inwOwnerList{}.anonymousOwner varchar(1), _inwOwnerList{}.coOwner varchar(16), _inwOwnerList{}.dateSituation varchar(9), _inwOwnerList{}.CRABadrID varchar(10), _inwParcelList{}.constructionIndication number(4,0), _inwParcelList{}.propertySituationIdf number(8,0), _inwParcelList{}.divCad number(5,0), _inwParcelList{}.section varchar(1),
      _inwParcelList{}.primaryNumber number(3,0), _inwParcelList{}.bisNumber number(2,0), _inwParcelList{}.exponentLetter varchar(1), _inwParcelList{}.exponentNumber number(3,0), _inwParcelList{}.partNumber varchar(5), _inwParcelList{}.capakey varchar(17), _inwParcelList{}.order varchar(4), _inwParcelList{}.nature varchar(3), _inwParcelList{}.descriptPrivate varchar(35), _inwParcelList{}.block varchar(2), _inwParcelList{}.floor varchar(2), _inwParcelList{}.floorSituation varchar(5), _inwParcelList{}.crossDetail varchar(20), _inwParcelList{}.matUtil varchar(1), _inwParcelList{}.notTaxedMatUtil varchar(3), _inwParcelList{}.nisCom varchar(6), _inwParcelList{}.street_situation varchar(20), _inwParcelList{}.street_translation varchar(1), _inwParcelList{}.street_code varchar(6), _inwParcelList{}.number varchar(6), _inwParcelList{}.polWa varchar(8), _inwParcelList{}.surfaceNotTaxable number(10,0), _inwParcelList{}.surfaceTaxable number(10,0), _inwParcelList{}.surfaceVerif varchar(2), _inwParcelList{}.constructionYear number(5,0), _inwParcelList{}.soilIndex number(2,0), _inwParcelList{}.soilRent varchar(2), _inwParcelList{}.cadastralIncomePerSurface number(3,0), _inwParcelList{}.cadastralIncomePerSurfaceOtherDi number(2,0), _inwParcelList{}.numberCadastralIncome number(1,0),
      _inwParcelList{}.charCadastralIncome varchar(1), _inwParcelList{}.cadastralIncome number(6,0), _inwParcelList{}.dateEndExoneration varchar(1), _inwParcelList{}.decrete varchar(1), _inwParcelList{}.constructionType varchar(2), _inwParcelList{}.floorNumberAboveground number(2,0), _inwParcelList{}.garret number(2,0), _inwParcelList{}.physModYear number(5,0), _inwParcelList{}.constructionQuality varchar(2), _inwParcelList{}.garageNumber number(2,0), _inwParcelList{}.centralHeating number(2,0), _inwParcelList{}.bathroomNumber number(2,0), _inwParcelList{}.housingUnitNumber number(2,0), _inwParcelList{}.placeNumber number(3,0), _inwParcelList{}.builtSurface number(5,0), _inwParcelList{}.usedSurface number(4,0), _inwParcelList{}.dateSituation varchar(9), _inwParcelList{}.aard varchar(10), _inwParcelList{}.bouwjaar varchar(25), _inwParcelList{}.GebouwType varchar(200)
AttributeRemover_2
    LIST_ATTRS = _huishoudList{} _huishoudList{}.AANTKIND _huishoudList{}.BURGSTAAT _huishoudList{}.BevRegID _huishoudList{}.GEBDAT _huishoudList{}.GESLACHT _huishoudList{}.GEZINSGROOTTE _huishoudList{}.HuishGrootte _huishoudList{}.HuishType _huishoudList{}.NATIONALITEIT _huishoudList{}.NAT_OUD _huishoudList{}.REFPERS _huishoudList{}.REGISTER _huishoudList{}.VERWERVING _inwEigenaarsList{} _inwEigenaarsList{}.officialId _inwList{} _inwList{}.AANTKIND _inwList{}.BURGSTAAT _inwList{}.BevRegID _inwList{}.CRAB_merge _inwList{}.CRABadrID _inwList{}.GEBDAT _inwList{}.GEMNM _inwList{}.GESLACHT _inwList{}.GEZINSGROOTTE _inwList{}.INDEX _inwList{}.NATIONALITEIT _inwList{}.NAT_OUD _inwList{}.NUMMER _inwList{}.PKANCODE _inwList{}.REFPERS _inwList{}.REGISTER _inwList{}.STRAATKODE _inwList{}.VERWERVING _inwList{}.gemeensch _inwList{}.sector _inwList{}.stadsdeel _inwList{}.wijknaam _inwOwnerList{} _inwParcelList{} _kadownersList{} _kadownersList{}.AARDADRPOS _kadownersList{}.AARDSUBADR _kadownersList{}.CRAB_merge _kadownersList{}.CRABadrID _kadownersList{}.GEMNM _kadownersList{}.HUISNR _kadownersList{}.HUISNRID _kadownersList{}.HUISNR_BEG _kadownersList{}.HUISNR_EIN _kadownersList{}.HUISNR_TIJ _kadownersList{}.INDEX _kadownersList{}.NISGEMCODE _kadownersList{}.NUMMER _kadownersList{}.PKANCODE _kadownersList{}.POSTKODE _kadownersList{}.STRAATKODE _kadownersList{}.STRAATNM _kadownersList{}.STRAATNMID _kadownersList{}.SUBADR _kadownersList{}.SUBADRES _kadownersList{}.SUBADRESID _kadownersList{}.SUBADR_BEG _kadownersList{}.SUBADR_EIN _kadownersList{}.SUBADR_TIJ _kadownersList{}.X _kadownersList{}.Y _kadownersList{}._matched_characters _kadownersList{}._matched_parts{} _kadownersList{}.adrType _kadownersList{}.anonymousOwner _kadownersList{}.birthdate _kadownersList{}.birthdate_partner _kadownersList{}.boxNumber _kadownersList{}.boxNumber_partner _kadownersList{}.coOwner _kadownersList{}.country _kadownersList{}.country_partner _kadownersList{}.firstName_partner _kadownersList{}.firstname _kadownersList{}.managedBy _kadownersList{}.municipality _kadownersList{}.municipality_partner _kadownersList{}.name _kadownersList{}.name_partner _kadownersList{}.number _kadownersList{}.number_partner _kadownersList{}.officialId _kadownersList{}.officialId_partner _kadownersList{}.order _kadownersList{}.partyType _kadownersList{}.propertySituationIdf _kadownersList{}.right _kadownersList{}.sector _kadownersList{}.stadsdeel _kadownersList{}.street _kadownersList{}.street_partner _kadownersList{}.wijknaam _kadownersList{}.zipCode _kadownersList{}.zipCode_partner _kadparcelList{} _kadparcelList{}.GebouwType _kadparcelList{}.aard _kadparcelList{}.bathroomNumber _kadparcelList{}.bisNumber _kadparcelList{}.block _kadparcelList{}.bouwjaar _kadparcelList{}.builtSurface _kadparcelList{}.cadastralIncome _kadparcelList{}.cadastralIncomePerSurface _kadparcelList{}.cadastralIncomePerSurfaceOtherDi _kadparcelList{}.capakey _kadparcelList{}.centralHeating _kadparcelList{}.charCadastralIncome _kadparcelList{}.constructionIndication _kadparcelList{}.constructionQuality _kadparcelList{}.constructionType _kadparcelList{}.constructionYear _kadparcelList{}.crossDetail _kadparcelList{}.dateEndExoneration _kadparcelList{}.decrete _kadparcelList{}.descriptPrivate _kadparcelList{}.divCad _kadparcelList{}.exponentLetter _kadparcelList{}.exponentNumber _kadparcelList{}.floor _kadparcelList{}.floorNumberAboveground _kadparcelList{}.floorSituation _kadparcelList{}.garageNumber _kadparcelList{}.garret _kadparcelList{}.housingUnitNumber _kadparcelList{}.matUtil _kadparcelList{}.nature _kadparcelList{}.notTaxedMatUtil _kadparcelList{}.number _kadparcelList{}.numberCadastralIncome _kadparcelList{}.order _kadparcelList{}.partNumber _kadparcelList{}.physModYear _kadparcelList{}.placeNumber _kadparcelList{}.polWa _kadparcelList{}.primaryNumber _kadparcelList{}.propertySituationIdf _kadparcelList{}.section _kadparcelList{}.soilIndex _kadparcelList{}.soilRent _kadparcelList{}.street_situation _kadparcelList{}.street_translation _kadparcelList{}.surfaceNotTaxable _kadparcelList{}.surfaceTaxable _kadparcelList{}.surfaceVerif _kadparcelList{}.usedSurface _onlyfirst{} _onlysecond{}
    -> Aggregator
Aggregator
    SEP = ,
    MODE = Geometry - Assemble One Level
    GROUP_BY = capakey
    ACCUM_ATTRS_NAME = Get Attributes From One Representative Feature
    AGGREGATE_TYPE = Homogeneous Collection (If Possible)
    ORDERED = No
    AGGREGATE -> FeatureMerger_5 [SUPPLIER]
AttributeRemover_3
    LIST_ATTRS = _gebouweenhList{} _gebouweenhList{}.AARDADRPOS _gebouweenhList{}.AARDSUBADR _gebouweenhList{}.CRABadrID _gebouweenhList{}.Domicilie _gebouweenhList{}.EenprsHh _gebouweenhList{}.Functie _gebouweenhList{}.GEMNM _gebouweenhList{}.GebouwType _gebouweenhList{}.GemeensHh _gebouweenhList{}.HUISNR _gebouweenhList{}.HUISNRID _gebouweenhList{}.HUISNR_BEG _gebouweenhList{}.HUISNR_EIN _gebouweenhList{}.HUISNR_TIJ _gebouweenhList{}.HandelID _gebouweenhList{}.MeerprsHh _gebouweenhList{}.NISGEMCODE _gebouweenhList{}.PKANCODE _gebouweenhList{}.ParticHh _gebouweenhList{}.STRAATNM _gebouweenhList{}.STRAATNMID _gebouweenhList{}.SUBADRES _gebouweenhList{}.SUBADRESID _gebouweenhList{}.SUBADR_BEG _gebouweenhList{}.SUBADR_EIN _gebouweenhList{}.SUBADR_TIJ _gebouweenhList{}.TypeEenh _gebouweenhList{}.Wooneenh _gebouweenhList{}.X _gebouweenhList{}.Y
    -> FeatureMerger_5 [REQUESTOR]
FeatureMerger_5
    JOIN_KEYS = @Value(capakey) @Value(capakey) AUTO
    MERGE_TYPE = Attributes Only
    IGNORE_NULLS = No
    SUPPLIERS_FIRST = No
    ATTR_CONFLICT_RES = Use Requestor
    ATTR_ACCUM_MODE = Merge Supplier
    LIST_NAME = _gebouweenhList
    REJECT_NULL_MISSING_KEYS = No
    PROCESS_DUPS = No
    MERGED -> 004_KAD_percelen (writer FFS_9)
    NOT_MERGED -> 004_KAD_percelen (writer FFS_9)
004_KAD_percelen (writer FFS_9)
    attributes: Gebouweenh number(3,0), Wooneenh number(3,0), constructionIndication varchar(254), capakey varchar(17), nature varchar(254), descriptPrivate varchar(254), constructionType varchar(254), housingUnitNumber number(3,0), _kadparcelList{}.constructionIndication number(4,0), _kadparcelList{}.propertySituationIdf number(8,0), _kadparcelList{}.divCad number(5,0), _kadparcelList{}.section varchar(1), _kadparcelList{}.primaryNumber number(3,0), _kadparcelList{}.bisNumber number(2,0), _kadparcelList{}.exponentLetter varchar(1), _kadparcelList{}.exponentNumber number(3,0), _kadparcelList{}.partNumber varchar(5), _kadparcelList{}.capakey varchar(17), _kadparcelList{}.order varchar(4), _kadparcelList{}.nature varchar(3), _kadparcelList{}.descriptPrivate varchar(35), _kadparcelList{}.block varchar(2), _kadparcelList{}.floor varchar(2), _kadparcelList{}.floorSituation varchar(5), _kadparcelList{}.crossDetail varchar(20), _kadparcelList{}.matUtil varchar(1), _kadparcelList{}.notTaxedMatUtil varchar(3), _kadparcelList{}.nisCom varchar(6), _kadparcelList{}.street_situation varchar(20), _kadparcelList{}.street_translation varchar(1),
      _kadparcelList{}.street_code varchar(6), _kadparcelList{}.number varchar(6), _kadparcelList{}.polWa varchar(8), _kadparcelList{}.surfaceNotTaxable number(10,0), _kadparcelList{}.surfaceTaxable number(10,0), _kadparcelList{}.surfaceVerif varchar(2), _kadparcelList{}.constructionYear number(5,0), _kadparcelList{}.soilIndex number(2,0), _kadparcelList{}.soilRent varchar(2), _kadparcelList{}.cadastralIncomePerSurface number(3,0), _kadparcelList{}.cadastralIncomePerSurfaceOtherDi number(2,0), _kadparcelList{}.numberCadastralIncome number(1,0), _kadparcelList{}.charCadastralIncome varchar(1), _kadparcelList{}.cadastralIncome number(6,0), _kadparcelList{}.dateEndExoneration varchar(1), _kadparcelList{}.decrete varchar(1), _kadparcelList{}.constructionType varchar(2), _kadparcelList{}.floorNumberAboveground number(2,0), _kadparcelList{}.garret number(2,0), _kadparcelList{}.physModYear number(5,0), _kadparcelList{}.constructionQuality varchar(2), _kadparcelList{}.garageNumber number(2,0), _kadparcelList{}.centralHeating number(2,0), _kadparcelList{}.bathroomNumber number(2,0), _kadparcelList{}.housingUnitNumber number(2,0), _kadparcelList{}.placeNumber number(3,0), _kadparcelList{}.builtSurface number(5,0), _kadparcelList{}.usedSurface number(4,0), _kadparcelList{}.dateSituation varchar(9), _kadparcelList{}.aard varchar(10),
      _kadparcelList{}.bouwjaar varchar(25), _kadparcelList{}.GebouwType varchar(200), ParticHh number(3,0), EenprsHh number(3,0), MeerprsHh number(3,0), GemeensHh number(3,0), GebouwType varchar(150), _gebouweenhList{}.TypeEenh varchar(60), _gebouweenhList{}.Functie varchar(60), _gebouweenhList{}.HandelID varchar(10), _gebouweenhList{}.Domicilie varchar(60), _gebouweenhList{}.CRABadrID varchar(10), _gebouweenhList{}.ParticHh number(3,0), _gebouweenhList{}.EenprsHh number(3,0), _gebouweenhList{}.MeerprsHh number(3,0), _gebouweenhList{}.GemeensHh number(3,0), _gebouweenhList{}.STRAATNM varchar(254), _gebouweenhList{}.HUISNR varchar(10), _gebouweenhList{}.SUBADRES varchar(5), _gebouweenhList{}.PKANCODE number(11,0), _gebouweenhList{}.GEMNM varchar(4), _gebouweenhList{}.GebouwType varchar(150), _gebouweenhList{}.EigWoning varchar(30), _gebouweenhList{}.InwEigenaars number(4,0)

Bookmark: INPUT KAD_owners
000_KAD_owner (reader FFS_5)
    attributes: propertySituationIdf varchar(9), order varchar(3), partyType varchar(3), right varchar(51), right_trad varchar(51), managedBy number(2,0), officialId varchar(12), name varchar(80), firstname varchar(12), birthdate varchar(11), country varchar(3), zipCode varchar(4), municipality_fr varchar(30), municipality_nl varchar(30), street_fr varchar(30), street_nl varchar(30), number varchar(5), boxNumber varchar(5), officialId_partner varchar(13), name_partner varchar(23), firstName_partner varchar(13), birthdate_partner varchar(11), country_partner varchar(3), zipCode_partner varchar(5), municipality_partner_fr varchar(30), municipality_partner_nl varchar(30), street_partner_fr varchar(30), street_partner_nl varchar(30), number_partner varchar(20), boxNumber_partner varchar(5),
      coOwner varchar(16), anonymousOwner varchar(1), dateSituation varchar(9)
    -> AttributeCreator_4
001_BevReg_CRAB (reader FFS_2)
    attributes: POSTKODE varchar(4), STRAATKODE varchar(8), NUMMER varchar(5), INDEX varchar(5), GEBDAT varchar(11), GESLACHT varchar(2), NATIONALITEIT number(4,0), VERWERVING number(3,0), REFPERS varchar(2), GEZINSGROOTTE number(3,0), AANTKIND number(3,0), BURGSTAAT varchar(15), NAT_OUD number(4,0), REGISTER varchar(6), sector varchar(5), stadsdeel varchar(16), wijknaam varchar(30), gemeensch varchar(12), BevRegID varchar(10), CRAB_merge varchar(254), CRABadrID varchar(10), GEMNM varchar(4), HUISNR varchar(10), PKANCODE number(11,0), STRAATNM varchar(255), SUBADRES varchar(255)
    -> AttributeKeeper

Bookmark: Format boxnumber
StringSearcher
    REGEXP = ^[0-9]+$
    STRING_TO_SEARCH = @Value(boxNumber)
    CASE = no
    MATCHED_RESULT_ATTR = _matched_characters
    MATCHED_PARTS_ATTR = _matched_parts
    MATCHED -> StringFormatter
    NOT_MATCHED -> FeatureMerger [REQUESTOR]
StringFormatter
    SRC_ATTRS = boxNumber
    FORMAT = 04s
    -> AttributeRemover
AttributeRemover
    REMOVE_ATTRS = _matched_characters
    LIST_ATTRS = _matched_parts{}
    -> FeatureMerger [REQUESTOR]

Bookmark: Testen eigenaars niet in BevReg
TestFilter_2
    DEFAULT_VALUE = <UNFILTERED>
    TEST_LIST = BOOL_OP,OR,COMPOSITE_TEST,<Unused>,TEST_CLAUSE,"TEST @Value(right) LIKE -BE %",Blote eigendom
TestFilter_2_Blote_eigendom: Inspector
TestFilter_2__Unfiltered_: Inspector

Bookmark: Format BevReg NUMMER INDEX to CRAB HUISNR SUBADR
StringSearcher_2
    REGEXP = ^[0-9]+$
    STRING_TO_SEARCH = @Value(boxNumber)
    CASE = no
    MATCHED_RESULT_ATTR = _matched_characters
    MATCHED_PARTS_ATTR = _matched_parts
    MATCHED -> AttributeCreator
    NOT_MATCHED -> StringSearcher_3
AttributeCreator
    ATTR_LIST = SUBADR,@Value(boxNumber),HUISNR,@TrimLeft(@Value(number),0)
    -> AttributeRemover_5
StringSearcher_3
    REGEXP = ([a-z]|[A-Z])
    STRING_TO_SEARCH = @Value(boxNumber)
    CASE = no
    MATCHED_RESULT_ATTR = _matched_characters
    MATCHED_PARTS_ATTR = _matched_parts
    MATCHED -> AttributeCreator_3
    NOT_MATCHED -> AttributeRemover_5
AttributeCreator_3
    ATTR_LIST = HUISNR,@TrimLeft(@Value(number),0)@Value(_matched_characters),SUBADR,"FME_CONDITIONAL:DEFAULT_VALUE'_FME_NO_OP_'BOOL_OP;OR;COMPOSITE_TEST;<Unused>;TEST @Value(_matched_parts{1}) > 0'@PadLeft(@Value(_matched_parts{1}),4,0)'FME_NUM_CONDITIONS2___"
    -> AttributeRemover_5
AttributeRemover_5
    REMOVE_ATTRS = _matched_characters
    LIST_ATTRS = _matched_parts{}
    -> FeatureMerger_2 [REQUESTOR]

Bookmark: INPUT ADRESSEN
000_CRAB_alladr (reader FFS_3)
    attributes: CRABadrID varchar(10), STRAATNMID number(11,0), STRAATNM varchar(255), HUISNRID number(11,0), HUISNR varchar(10), HUISNR_BEG varchar(20), HUISNR_TIJ varchar(20), HUISNR_EIN varchar(20), SUBADRESID number(11,0), SUBADRES varchar(255), SUBADR_BEG varchar(20), AARDSUBADR number(11,0), NISGEMCODE varchar(5), PKANCODE number(11,0), GEMNM varchar(4), AARDADRPOS number(11,0), X number(31,15), Y number(31,15), SUBADR_TIJ varchar(20), SUBADR_EIN varchar(20)
    -> StringSearcher_4
001_BevReg_adr_notCRAB (reader FFS_1)
    attributes: POSTKODE varchar(4), STRAATKODE varchar(8), NUMMER varchar(5), INDEX varchar(5), sector varchar(5), stadsdeel varchar(16), wijknaam varchar(30), CRAB_merge varchar(254), CRABadrID varchar(10), GEMNM varchar(4), HUISNR varchar(10), PKANCODE number(11,0), STRAATNM varchar(255), SUBADRES varchar(255), adrType varchar(4)
    -> StringSearcher_4

Bookmark: INPUT gebouweenheden_adressen
  _huishoudList{}
  _inwList{}
003_Gebouweenheden_Adressen (reader FFS_6)
    attributes: TypeEenh varchar(60), Functie varchar(60), Domicilie varchar(60), CRABadrID varchar(10), capakey varchar(17), ParticHh number(3,0), EenprsHh number(3,0), MeerprsHh number(3,0), GemeensHh number(3,0), HandelID varchar(10), _huishoudList{}.HuishType varchar(60), _huishoudList{}.HuishGrootte number(3,0), _huishoudList{}.GEBDAT varchar(11), _huishoudList{}.GESLACHT varchar(2), _huishoudList{}.NATIONALITEIT number(4,0), _huishoudList{}.VERWERVING number(3,0), _huishoudList{}.REFPERS varchar(2), _huishoudList{}.GEZINSGROOTTE number(3,0), _huishoudList{}.AANTKIND number(3,0), _huishoudList{}.BURGSTAAT varchar(15), _huishoudList{}.NAT_OUD number(4,0), _huishoudList{}.REGISTER varchar(6), _huishoudList{}.BevRegID varchar(10), STRAATNM varchar(255), HUISNR varchar(10), SUBADRES varchar(255), PKANCODE number(11,0), GEMNM varchar(4), Gebouweenh number(3,0), Wooneenh number(3,0),
      GebouwType varchar(150), _inwList{}.STRAATKODE varchar(8), _inwList{}.NUMMER varchar(5), _inwList{}.INDEX varchar(5), _inwList{}.GEBDAT varchar(11), _inwList{}.GESLACHT varchar(2), _inwList{}.NATIONALITEIT number(4,0), _inwList{}.VERWERVING number(3,0), _inwList{}.REFPERS varchar(2), _inwList{}.GEZINSGROOTTE number(3,0), _inwList{}.AANTKIND number(3,0), _inwList{}.BURGSTAAT varchar(15), _inwList{}.NAT_OUD number(4,0), _inwList{}.REGISTER varchar(6), _inwList{}.sector varchar(5), _inwList{}.stadsdeel varchar(16), _inwList{}.wijknaam varchar(30), _inwList{}.gemeensch varchar(12), _inwList{}.BevRegID varchar(10), _inwList{}.CRAB_merge varchar(254), _inwList{}.CRABadrID varchar(10), _inwList{}.GEMNM varchar(4), _inwList{}.PKANCODE number(11,0)
    -> GeometryExtractor

Bookmark: INPUT KADparcel_gebouweenheden
  _kadparcelList{}
  _gebouweenh{}
003_KADparcel_Gebouweenheden (reader FFS_4)
    attributes: Gebouweenh number(3,0), Wooneenh number(3,0), constructionIndication varchar(254), capakey varchar(17), nature varchar(254), descriptPrivate varchar(254), constructionType varchar(254), housingUnitNumber number(3,0), _kadparcelList{}.constructionIndication number(4,0), _kadparcelList{}.propertySituationIdf number(8,0), _kadparcelList{}.divCad number(5,0), _kadparcelList{}.section varchar(1), _kadparcelList{}.primaryNumber number(3,0), _kadparcelList{}.bisNumber number(2,0), _kadparcelList{}.exponentLetter varchar(1), _kadparcelList{}.exponentNumber number(3,0), _kadparcelList{}.partNumber varchar(5), _kadparcelList{}.capakey varchar(17), _kadparcelList{}.order varchar(4), _kadparcelList{}.nature varchar(3), _kadparcelList{}.descriptPrivate varchar(35), _kadparcelList{}.block varchar(2), _kadparcelList{}.floor varchar(2), _kadparcelList{}.floorSituation varchar(5), _kadparcelList{}.crossDetail varchar(20), _kadparcelList{}.matUtil varchar(1), _kadparcelList{}.notTaxedMatUtil varchar(3), _kadparcelList{}.nisCom varbinary(6), _kadparcelList{}.street_situation varchar(20), _kadparcelList{}.street_translation varchar(1),
      _kadparcelList{}.street_code varchar(6), _kadparcelList{}.number varchar(6), _kadparcelList{}.polWa varchar(8), _kadparcelList{}.surfaceNotTaxable number(10,0), _kadparcelList{}.surfaceTaxable number(10,0), _kadparcelList{}.surfaceVerif varchar(2), _kadparcelList{}.constructionYear number(5,0), _kadparcelList{}.soilIndex number(2,0), _kadparcelList{}.soilRent varchar(2), _kadparcelList{}.cadastralIncomePerSurface number(3,0), _kadparcelList{}.cadastralIncomePerSurfaceOtherDi number(2,0), _kadparcelList{}.numberCadastralIncome number(1,0), _kadparcelList{}.charCadastralIncome varchar(1), _kadparcelList{}.cadastralIncome number(6,0), _kadparcelList{}.dateEndExoneration varchar(1), _kadparcelList{}.decrete varchar(1), _kadparcelList{}.constructionType varchar(2), _kadparcelList{}.floorNumberAboveground number(2,0), _kadparcelList{}.garret number(2,0), _kadparcelList{}.physModYear number(5,0), _kadparcelList{}.constructionQuality varchar(2), _kadparcelList{}.garageNumber number(2,0), _kadparcelList{}.centralHeating number(2,0), _kadparcelList{}.bathroomNumber number(2,0), _kadparcelList{}.housingUnitNumber number(2,0), _kadparcelList{}.placeNumber number(3,0), _kadparcelList{}.builtSurface number(5,0), _kadparcelList{}.usedSurface number(4,0), _kadparcelList{}.aard varchar(10), _kadparcelList{}.bouwjaar varchar(25),
      _kadparcelList{}.GebouwType varchar(200), _kadparcelList{}.dateSituation varchar(9), ParticHh number(3,0), EenprsHh number(3,0), MeerprsHh number(3,0), GemeensHh number(3,0), GebouwType varchar(150), _gebouweenhList{}.TypeEenh varchar(60), _gebouweenhList{}.Functie varchar(60), _gebouweenhList{}.HandelID varchar(10), _gebouweenhList{}.Domicilie varchar(60), _gebouweenhList{}.CRABadrID varchar(10), _gebouweenhList{}.ParticHh number(3,0), _gebouweenhList{}.EenprsHh number(3,0), _gebouweenhList{}.MeerprsHh number(3,0), _gebouweenhList{}.GemeensHh number(3,0), _gebouweenhList{}.STRAATNMID number(11,0), _gebouweenhList{}.STRAATNM varchar(254), _gebouweenhList{}.HUISNRID number(11,0), _gebouweenhList{}.HUISNR varchar(10), _gebouweenhList{}.HUISNR_BEG varchar(20), _gebouweenhList{}.HUISNR_TIJ varchar(20), _gebouweenhList{}.HUISNR_EIN varchar(20), _gebouweenhList{}.SUBADRESID number(11,0), _gebouweenhList{}.SUBADRES varchar(5), _gebouweenhList{}.SUBADR_BEG varchar(20), _gebouweenhList{}.AARDSUBADR number(11,0), _gebouweenhList{}.NISGEMCODE varchar(5), _gebouweenhList{}.PKANCODE number(11,0), _gebouweenhList{}.GEMNM varchar(4),
      _gebouweenhList{}.AARDADRPOS number(11,0), _gebouweenhList{}.X number(31,15), _gebouweenhList{}.Y number(31,15), _gebouweenhList{}.SUBADR_TIJ varchar(20), _gebouweenhList{}.SUBADR_EIN varchar(20), _gebouweenhList{}.Wooneenh varchar(3), _gebouweenhList{}.GebouwType varchar(150)
    -> AttributeRemover_3
    -> AttributeKeeper_2

FME custom transformer ListComparer
Compares the elements of two list attributes. Elements that occur in both lists are written to the output list attribute _both{}. Elements that occur only in one of the lists are written to resp. _onlyfirst{} and _onlysecond{}.
Parameters:
Mode: 
* 1 to many (default): dupplicate values in first list are considered as different values. 
* many to one: if dupplicates occur first list, the corresponding values in second list name are dupplicated in _bothsecond{}
First List Attribute: Specify the first list attribute.
Second List Attribute: Specify the second list attribute.
Both List Name: Specify the name of the list attribute containing the identical elements. (Excluding curly braces {}.)
Only First List Name: Specify the name of the list attribute containing the elements that occur only in the first list. (Excluding curly braces {}.)
Only Second List Name: Specify the name of the list attribute containing the elements that occur only in the first list. (Excluding curly braces {}.) 
Note
Duplicate list elements are compared as individual elements. 
This transformer cannot be applied to
- nested lists; such as "_list{}.sub{}"
- lists missing some elements; such as [<missing>, 1, 2, <missing>, 4, 5]

Parameters:
- MODE = DEFAULT   # One to Many (Default),DEFAULT%Many to One,MANYtoONE Mode
- FIRST_LIST_ATTR =   # " " First List Attribute
- SECOND_LIST_ATTR =   # " " Second List Attribute
- LIST_NAME_BOTHFIRST = _bothfirst   # List Name Both (copy of elements of first list)
- LIST_NAME_ONLYFIRST = _onlyfirst   # List Name OnlyFirst
- LIST_NAME_ONLYSECOND = _onlysecond   # List Name OnlySecond
- LIST_NAME_BOTHSECOND = _bothsecond   # List Name Both (copy of elements of second list)

Input (input)
    -> ParameterFetcher
ParameterFetcher
    ATTR_LIST = listcomparer.mode {$(MODE)} listcomparer.first_list_attr {$(FIRST_LIST_ATTR)} listcomparer.second_list_attr {$(SECOND_LIST_ATTR)}
    -> PythonCaller
PythonCaller
    NEW_ATTRIBUTES = listcomparer.bothfirst{} listcomparer.bothsecond{} listcomparer.onlyfirst{} listcomparer.onlysecond{}
    PYTHONSOURCE:
      import fmeobjects, locale, re

      class ListComparer(object):
          def __init__(self):
              self.enc = locale.getdefaultlocale()[1]

          def input(self, feature):
              mode = feature.getAttribute('listcomparer.mode')
              list1 = map(str, self.createList(feature, 'listcomparer.first_list_attr'))
              list2 = map(str, self.createList(feature, 'listcomparer.second_list_attr'))
              list1key = feature.getAttribute('listcomparer.first_list_attr')
              list2key = feature.getAttribute('listcomparer.second_list_attr')
              list1name_match = re.match(r'^(.+\{)(\})', list1key)
              list2name_match = re.match(r'^(.+\{)(\})', list2key)
              if not list1name_match:
                  raise fmeobjects.FMEException('listcomparer: Invalid First List Attribute')
              else:
                  list1name = list1name_match.group(1) + list1name_match.group(2)
              if not list2name_match:
                  raise fmeobjects.FMEException('listcomparer: Invalid Second List Attribute')
              else:
                  list2name = list2name_match.group(1) + list2name_match.group(2)

              iboth, ionly1, ionly2 = 0, 0, 0
              if mode == 'DEFAULT':
                  comparelist = []
                  for i, value in enumerate (list(list2)):
                      comparelist.append([value, 'notused'])
                  for i, value in enumerate (list1):
                      src_basename1 = list1name_match.group(1) + '%d' % (i) + '}'
                      alllist1attr = self.getlistattr(feature, list1name, i)
                      if alllist1attr == []:
                          alllist1attr.append('')

                      if ([value, 'notused']) in comparelist:
                          dest_basename1 = 'listcomparer.bothfirst{%d}' % (iboth)
                          dest_basename2 = 'listcomparer.bothsecond{%d}' % (iboth)
                          j = list2.index(value)
                          src_basename2 = list2name_match.group(1) + '%d' % (j) + '}'
                          alllist2attr = self.getlistattr(feature, list2name, j)
                          if alllist2attr == []:
                              alllist2attr.append('')
                          for name in alllist1attr:
                              attrvalue = feature.getAttribute(src_basename1 + name)
                              if attrvalue == None:
                                  feature.setAttributeNullWithType(name, fmeobjects.FME_ATTR_UNDEFINED)
                              else:
                                  feature.setAttribute(dest_basename1 + name, attrvalue)
                          for name in alllist2attr:
                              attrvalue = feature.getAttribute(src_basename2 + name)
                              if attrvalue == None:
                                  feature.setAttributeNullWithType(name, fmeobjects.FME_ATTR_UNDEFINED)
                              else:
                                  feature.setAttribute(dest_basename2 + name, attrvalue)
                          iboth += 1
                          comparelist[comparelist.index([value, 'notused'])][1] ='used'

                      else:
      #                    if value==None:
      #                        print 'None only in list1'
      #                    else:
      #                        print value + 'only in list1'
                          dest_basename = 'listcomparer.onlyfirst{%d}' % (ionly1)
                          for name in alllist1attr:
                              value = feature.getAttribute(src_basename1 + name)
                              if value == None:
                                  feature.setAttributeNullWithType(name, fmeobjects.FME_ATTR_UNDEFINED)
                              else:
                                  feature.setAttribute(dest_basename + name, value)
                          ionly1 += 1

                  list2rev = list(list2)
                  list2rev.reverse()
                  for i, valuelst in enumerate(comparelist):
                      if valuelst[1] == 'notused':
                          value = valuelst[0]
      #                    if value==None:
      #                        print 'None in list2 only'
      #                    else:
      #                        print value + 'in list2 only'
                          src_basename = list2name_match.group(1) + '%d' % (i) + '}'
                          alllistattr = self.getlistattr(feature, list2name, i)
                          if alllistattr == []:
                              alllistattr.append('')

                          dest_basename = 'listcomparer.onlysecond{%d}' % (ionly2)
                          for name in alllistattr:
                              value = feature.getAttribute(src_basename + name)
                              if value == None:
                                  feature.setAttributeNullWithType(name, fmeobjects.FME_ATTR_UNDEFINED)
                              else:
                                  feature.setAttribute(dest_basename + name, value)
                          ionly2 += 1


              elif mode == 'MANYtoONE':
                  comparelist = []
                  for i, value in enumerate (list(list2)):
                      comparelist.append([value, 'notused'])
                  for i, value in enumerate (list1):
                      src_basename1 = list1name_match.group(1) + '%d' % (i) + '}'
                      alllist1attr = self.getlistattr(feature, list1name, i)
                      if alllist1attr == []:
                          alllist1attr.append('')

                      if value in [elem[0] for elem in comparelist]:
                          dest_basename1 = 'listcomparer.bothfirst{%d}' % (iboth)
                          dest_basename2 = 'listcomparer.bothsecond{%d}' % (iboth)
                          j = list2.index(value)
                          src_basename2 = list2name_match.group(1) + '%d' % (j) + '}'
                          alllist2attr = self.getlistattr(feature, list2name, j)
                          if alllist2attr == []:
                              alllist2attr.append('')
                          for name in alllist1attr:
                              attrvalue = feature.getAttribute(src_basename1 + name)
                              if attrvalue == None:
                                  feature.setAttributeNullWithType(name, fmeobjects.FME_ATTR_UNDEFINED)
                              else:
                                  feature.setAttribute(dest_basename1 + name, attrvalue)
                          for name in alllist2attr:
                              attrvalue = feature.getAttribute(src_basename2 + name)
                              if attrvalue == None:
                                  feature.setAttributeNullWithType(name, fmeobjects.FME_ATTR_UNDEFINED)
                              else:
                                  feature.setAttribute(dest_basename2 + name, attrvalue)
                          iboth += 1
                          comparelist[[elem[0] for elem in comparelist].index(value)][1] = 'used'

                      else:
      #                    if value==None:
      #                        print 'None only in list1'
      #                    else:
      #                        print value + 'only in list1'
                          dest_basename = 'listcomparer.onlyfirst{%d}' % (ionly1)
                          for name in alllist1attr:
                              value = feature.getAttribute(src_basename1 + name)
                              if value == None:
                                  feature.setAttributeNullWithType(name, fmeobjects.FME_ATTR_UNDEFINED)
                              else:
                                  feature.setAttribute(dest_basename + name, value)
                          ionly1 += 1

                  list2rev = list(list2)
                  list2rev.reverse()
                  for i, valuelst in enumerate(comparelist):
                      if valuelst[1] == 'notused':
                          value = valuelst[0]
      #                    if value==None:
      #                        print 'None in list2 only'
      #                    else:
      #                        print value + 'in list2 only'
                          src_basename = list2name_match.group(1) + '%d' % (i) + '}'
                          alllistattr = self.getlistattr(feature, list2name, i)
                          if alllistattr == []:
                              alllistattr.append('')

                          dest_basename = 'listcomparer.onlysecond{%d}' % (ionly2)
                          for name in alllistattr:
                              value = feature.getAttribute(src_basename + name)
                              if value == None:
                                  feature.setAttributeNullWithType(name, fmeobjects.FME_ATTR_UNDEFINED)
                              else:
                                  feature.setAttribute(dest_basename + name, value)
                          ionly2 += 1
              else:
                  raise fmeobjects.FMEException('listcomparer: Unsupported Mode')
              self.pyoutput(feature)

          def getlistattr(self, feature, listattrname, index):
              allattr = feature.getAllAttributeNames()
              listattrname_parts = re.match(r'^(.+\{)(\})', listattrname)
              if listattrname_parts:
                  existlistattrnames = []
                  existlistindex = []
                  regex = '(^' + listattrname_parts.group(1) + ')(' + str(index) + ')(' + listattrname_parts.group(2) + ')' + '(\..+)?'
                  for attr in allattr:
                      m = re.match(r'%s' % regex, attr)
                      if m:
                           existlistattrnames.append(m.group(4))
      #                if not(m.group(2) in existlistindex):
      #                     existlistindex.append(m.group(2))
                  return existlistattrnames


          def createList(self, feature, listAttr):
              listName = feature.getAttribute(listAttr)
              if isinstance(listName, unicode):
                  listName = listName.encode(self.enc)
              m = re.match(r'^(.+\{)(\}.*)$', listName)
              s, front, index, back = [], m.group(1), 0, m.group(2)
              listlength = self.getlistlength(feature, listName)
              while index < listlength:
                  name = '%s%d%s' % (front, index, back)
                  isNull, isMissing, type = feature.getAttributeNullMissingAndType(name)
                  if isMissing:
                      s.append(None) #break
                  else:
                      s.append(None if isNull else feature.getAttribute(name))
                  index += 1
              return s

          def getlistlength(self, feature, listAttr):
              allattr = feature.getAllAttributeNames()
              listattrname_parts = re.match(r'^(.+\{)(\})', listAttr)
              if listattrname_parts:
                  existlistindex = []
                  regex = '(^' + listattrname_parts.group(1) + ')(\d+)(' + listattrname_parts.group(2) + ')' + '(\..+)?'
                  for attr in allattr:
                      m = re.match(r'%s' % regex, attr)
                      if m and not(m.group(2) in existlistindex):
                          existlistindex.append(m.group(2))
                  return len(existlistindex)
    PYTHONSYMBOL = ListComparer
    -> ListRenamer
ListRenamer
    NEW_LIST_NAME = $(LIST_NAME_BOTHFIRST)
    TYPE = List
    LIST_NAME = listcomparer.bothfirst
    -> ListRenamer_4
ListRenamer_4
    NEW_LIST_NAME = $(LIST_NAME_BOTHSECOND)
    TYPE = List
    LIST_NAME = listcomparer.bothsecond
    -> ListRenamer_2
ListRenamer_2
    NEW_LIST_NAME = $(LIST_NAME_ONLYFIRST)
    TYPE = List
    LIST_NAME = listcomparer.onlyfirst
    -> ListRenamer_3
ListRenamer_3
    NEW_LIST_NAME = $(LIST_NAME_ONLYSECOND)
    TYPE = List
    LIST_NAME = listcomparer.onlysecond
    -> BulkAttributeRemover
BulkAttributeRemover
    ATTR_EXP = ^listcomparer.
    -> Output (output)
Output (output)
