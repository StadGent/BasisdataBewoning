FME workspace 000_BEW_BevRegbasisdata.fmw
Title: 000_BEW_BevRegbasisdata
Description: Bewerkingen: 
Aanmaak BevRegID 
Toevoegen Straatnamen aan export bevolkingsregister
History: 2016-10-06,Jonas Verstraete,Initial version

Parameters:
- DestDataset_FFS = ..\data\intermediate\000\000_BevReg.ffs   # Destination FME Feature Store (FFS) File
- SourceDataset_CSV_4 = ..\data\input\BevReg_extr.csv   # Source CSV (Comma Separated Value) File(s)
- SourceDataset_CSV = ..\data\input\CRAB_RijksregisterStraat.csv   # Source CSV (Comma Separated Value) File(s)

Readers:
- CSV_1: CSV from $(SourceDataset_CSV_4)
- CSV_2: CSV from $(SourceDataset_CSV)

Writers:
- FFS_1: FFS to $(DestDataset_FFS)

Note: 000_BEW_BevRegbasisdata.fmw / Bewerkingen: / Aanmaak BevRegID / Toevoegen Straatnamen aan export bevolkingsregister
BevReg_extr (reader CSV_1)
    attributes: POSTKODE number(5,0), STRAATKODE number(9,0), NUMMER number(5,0), INDEX char(5), GEBDAT char(11), GESLACHT char(2), NATIONALITEIT number(4,0), VERWERVING number(3,0), REFPERS char(2), GEZINSGROOTTE number(2,0), AANTKIND number(2,0), BURGSTAAT char(15), NAT_OUD number(4,0), REGISTER char(6), sector char(5), stadsdeel char(16), wijknaam char(30), gemeensch char(12)
    -> BevRegID
BevRegID: Counter
    SCOPE = Local
    CNT_ATTR = BevRegID
    DOMAIN = counter
    START = 1
    -> FeatureMerger [REQUESTOR]
CRAB_RijksregisterStraat (reader CSV_2)
    attributes: StraatCode number(5,0), StraatId number(6,0), Straatnaam char(35), SubkantonCode number(5,0), NISGemeenteCode number(6,0), Gemeente char(5)
    -> AttributeRenamer
AttributeRenamer
    ATTR_TABLE = RENAME_SET_DEFAULT NISGemeenteCode > NISGemeente
    -> AttributeCreator
AttributeCreator
    ATTR_TABLE = SET_TO STRAATKODE = @Value(SubkantonCode)@PadLeft(@Value(StraatCode),4,0)
    -> FeatureMerger [SUPPLIER]
FeatureMerger
    SUPPLIER_PREFIX = CRAB_
    MERGE_TYPE = Attributes Only
    PROCESS_DUPS = No
    IGNORE_NULLS = No
    ATTR_ACCUM_MODE = Prefix Supplier
    SUPPLIERS_FIRST = No
    JOIN_KEYS = @Value(STRAATKODE) @Value(STRAATKODE) AUTO
    MERGED -> 000_BevReg (writer FFS_1)
    NOT_MERGED -> 000_BevReg (writer FFS_1)
000_BevReg (writer FFS_1)
    attributes: POSTKODE varchar(4), STRAATKODE varchar(8), NUMMER varchar(5), INDEX varchar(5), GEBDAT varchar(11), GESLACHT varchar(2), NATIONALITEIT number(4,0), VERWERVING number(3,0), REFPERS varchar(2), GEZINSGROOTTE number(3,0), AANTKIND number(3,0), BURGSTAAT varchar(15), NAT_OUD number(4,0), REGISTER varchar(6), sector varchar(5), stadsdeel varchar(16), wijknaam varchar(30), gemeensch varchar(12), BevRegID varchar(10), CRAB_StraatId varchar(5), CRAB_SubkantonCode varchar(4), CRAB_Straatnaam char(100), CRAB_NISGemeente char(5), CRAB_Gemeente char(50)
