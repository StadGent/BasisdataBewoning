FME workspace 000_BEW_CRABbasisdata.fmw
Title: 000_BEW_CRABbasisdata
Description: Bewerkingen: 
Aanmaak CRABadrID 
Koppeling CRAB basistabellen obv CRAB-datastructuur
Usage: PARAMETERS
    [Toestand]: geef gewenste toestandsdatum (%Y%m%d)
History: 2016-10-06,Jonas Verstraete,Initial version

Parameters:
- Toestand = 20150101   # Toestand (%Y%m%d)
- DestDataset_SHAPE = ..\data\intermediate\000   # Destination Esri Shape Folder
- DestDataset_FFS = ..\data\intermediate\000\000_CRAB_alladr.ffs   # Destination FME Feature Store (FFS) File
- SourceDataset_CSV_10 = ..\data\input\huisnummer.csv   # Source CSV (Comma Separated Value) File(s)
- SourceDataset_CSV = ..\data\input\subadres.csv   # Source CSV (Comma Separated Value) File(s)
- SourceDataset_CSV_9 = ..\data\input\adrespositie.csv   # Source CSV (Comma Separated Value) File(s)
- SourceDataset_CSV_11 = ..\data\input\straatnaam.csv   # Source CSV (Comma Separated Value) File(s)
- SourceDataset_CSV_7 = ..\data\input\postkantoncode.csv   # Source CSV (Comma Separated Value) File(s)

Readers:
- CSV_1: CSV from $(SourceDataset_CSV_10)
- CSV_2: CSV from $(SourceDataset_CSV)
- CSV_3: CSV from $(SourceDataset_CSV_9)
- CSV_4: CSV from $(SourceDataset_CSV_11)
- CSV_5: CSV from $(SourceDataset_CSV_7)

Writers:
- SHAPE_1: SHAPE to $(DestDataset_SHAPE)
- FFS_1: FFS to $(DestDataset_FFS)

Note: CRAB Gent / - In Gent worden momenteel geen aparte adreslocaties aangemaakt voor subadressen. Adreslocatie is steeds afkomstig van huisnummer (hoofdadres) / >> enkel adreslocaties met AARD = 2 gebruikt voor koppeling / - Een hoofdadres waaraan subadressen hangen maar die ook op zichzelf bestaat (bvb. winkel onder appartement) kan niet worden gefilterd uit de tabellen / >> als een hoofdadres wordt gekoppeld aan een subadres, wordt het hoofdadres niet meer apart gebruikt / (zie featuremerger Huisnr to subadres) / deze worden in de praktijk in Gent zo weinig mogelijk gebruikt maar bestaan wel al. / deze kunnen ook bestaan in CRAB (bedoeld voor gezamelijk gedeelte van gebouw) / >> er wordt nog bekeken met IV of een aanduiding van hoofdadres/subadres kan worden opgenomen. / - TIJD: invoermoment. Nodig om wijzigingen te detecteren in bvb VESTA / - BEGINDATUM: de datum waarop het adres officieel is geworden. De CRAB databank (in deze structuur) dateert van 2005. / 01/01/1830 wordt gebruikt voor alle adressen die voor 2005 reeds aanwezig waren / 01/01/2001 werd ook gebruikt om correcties aan te geven. / >> kan dus niet als correcte begindatum worden gebruikt / >> wel correct als de begintijd (=invoermoment) van een huisnummer na de CRAB validatie valt (24/11/2014) / https://www.agiv.be/producten/crab/meer-info-over-crab/gebruik-van-het-crab/crab-raadpleegdiensten/ws-crab
Note: Enkel AARD = 2 (huisnummer)
TestFilter_4
    TEST_LIST = BOOL_OP,OR,COMPOSITE_TEST,<Unused>,TEST_CLAUSE,"TEST @Value(AARD) = 1",@Value(AARD) = 1,BOOL_OP,OR,COMPOSITE_TEST,<Unused>,TEST_CLAUSE,"TEST @Value(AARD) = 2",@Value(AARD) = 2
    DEFAULT_VALUE = <UNFILTERED>
    @Value(AARD) = 2 -> DateFormatter_2
Note: 000_BEW_CRABbasisdata.fmw / Bewerkingen: / Aanmaak CRABadrID / Koppeling CRAB basistabellen obv CRAB-datastructuur / PARAMETERS / [Toestand]: geef gewenste toestandsdatum (%Y%m%d)
DateFormatter_2
    SRCFMT = %Y%m%d%H%M%S
    FMT = FME Date (%Y%m%d)
    INVALID_DATE_VALUE = _FME_NO_OP_
    DATE_ATTR = EINDDATUM,BEGINDATUM
    -> AttributeExposer
    -> TestFilter_5
Note: Filter einddatum > gewenste toestand / begindatum <= gewenste toestand
TestFilter_5
    TEST_LIST:
      BOOL_OP,COMPOSITE,COMPOSITE_TEST,"""(1 OR 2 OR 3 OR 4) AND 5""",TEST_CLAUSE,"TEST @Value(EINDDATUM) > $(Toestand)
      TEST EINDDATUM ATTRIBUTE_VALUE_NULL """"
      TEST EINDDATUM ATTRIBUTE_IS_MISSING """"
      TEST EINDDATUM ATTRIBUTE_IS_EMPTY """"
      TEST @Value(BEGINDATUM) <= $(Toestand)",> $(Toestand)
    DEFAULT_VALUE = <UNFILTERED>
    > $(Toestand) -> FeatureTypeFilter
    <UNFILTERED> -> TestFilter_5__Unfiltered_
FeatureTypeFilter
    ATTRIBUTES = <BLANK>,<UNFILTERED>,subadres,straatnaam,postkantoncode,huisnummer,adrespositie
    subadres -> BulkAttributeRenamer_2
    straatnaam -> BulkAttributeRenamer_4
    postkantoncode -> BulkAttributeRenamer_5
    huisnummer -> BulkAttributeRenamer
    adrespositie -> BulkAttributeRenamer_3
BulkAttributeRenamer_2
    PATTERN_ACTION_DISP = Add String Prefix
    REPLACE_STR = SUBADR_
    ATTRLIST = BEGINDATUM BEWERKING EINDDATUM ID ORGANISATIE TIJD
    ATTRCHOICE = Selected Attributes
    -> FeatureMerger [REQUESTOR]
BulkAttributeRenamer
    PATTERN_ACTION_DISP = Add String Prefix
    REPLACE_STR = HUISNR_
    ATTRLIST = BEGINDATUM BEWERKING EINDDATUM ID ORGANISATIE TIJD
    ATTRCHOICE = Selected Attributes
    -> FeatureMerger_2 [REQUESTOR]
BulkAttributeRenamer_3
    PATTERN_ACTION_DISP = Add String Prefix
    REPLACE_STR = ADRPOS_
    ATTRLIST = BEGINDATUM BEWERKING EINDDATUM HERKOMST ID ORGANISATIE TIJD
    ATTRCHOICE = Selected Attributes
    -> FeatureMerger_2 [SUPPLIER]
Note: Adreslocatie to Huisnummer
FeatureMerger_2
    MERGE_TYPE = Attributes Only
    ATTR_CONFLICT_RES = Use Requestor
    PROCESS_DUPS = No
    IGNORE_NULLS = No
    ATTR_ACCUM_MODE = Merge Supplier
    SUPPLIERS_FIRST = No
    JOIN_KEYS = @Value(HUISNUMMERID) @Value(ADRESID) AUTO
    MERGED -> FeatureMerger [SUPPLIER]
Note: Subadres to Huisnummer
FeatureMerger
    MERGE_TYPE = Attributes Only
    ATTR_CONFLICT_RES = Use Requestor
    PROCESS_DUPS = Yes
    IGNORE_NULLS = No
    ATTR_ACCUM_MODE = Merge Supplier
    SUPPLIERS_FIRST = No
    GEOM_TYPE = Build Polygons
    JOIN_KEYS = @Value(HUISNUMMERID) @Value(HUISNUMMERID) AUTO
    MERGED -> FeatureMerger_3 [REQUESTOR]
    UNREFERENCED -> FeatureMerger_3 [REQUESTOR]
BulkAttributeRenamer_4
    PATTERN_ACTION_DISP = Add String Prefix
    REPLACE_STR = STRAAT_
    ATTRLIST = BEGINDATUM BEWERKING EINDDATUM ID ORGANISATIE TIJD
    ATTRCHOICE = Selected Attributes
    -> FeatureMerger_3 [SUPPLIER]
Note: Straat to Adres
FeatureMerger_3
    MERGE_TYPE = Attributes Only
    ATTR_CONFLICT_RES = Use Requestor
    PROCESS_DUPS = No
    IGNORE_NULLS = No
    ATTR_ACCUM_MODE = Merge Supplier
    SUPPLIERS_FIRST = No
    JOIN_KEYS = @Value(STRAATNAAMID) @Value(STRAATNAAMID) AUTO
    MERGED -> FeatureMerger_4 [REQUESTOR]
BulkAttributeRenamer_5
    PATTERN_ACTION_DISP = Add String Prefix
    REPLACE_STR = PKAN_
    ATTRLIST = BEGINDATUM BEWERKING EINDDATUM ID ORGANISATIE TIJD
    ATTRCHOICE = Selected Attributes
    -> FeatureMerger_4 [SUPPLIER]
Note: PostKanton to Adres
FeatureMerger_4
    MERGE_TYPE = Attributes Only
    ATTR_CONFLICT_RES = Use Requestor
    PROCESS_DUPS = No
    IGNORE_NULLS = No
    ATTR_ACCUM_MODE = Merge Supplier
    SUPPLIERS_FIRST = No
    JOIN_KEYS = @Value(HUISNUMMERID) @Value(HUISNUMMERID) AUTO
    MERGED -> VertexCreator
Note: Create point
VertexCreator
    YVAL = @Value(OG_COORD_Y)
    INDEX = 0
    MODE_NAME = Add Point
    XVAL = @Value(OG_COORD_X)
    -> AttributeRenamer
AttributeRenamer
    ATTR_LIST = HUISNUMMERID,HUISNRID,,HUISNR_BEGINDATUM,HUISNR_BEG,,HUISNR_TIJD,HUISNR_TIJ,,HUISNUMMER,HUISNR,,NISGEMEENTECODE,NISGEMCODE,,POSTKANTONCODE,PKANCODE,,STRAATNAAMID,STRAATNMID,,STRAATNAAM,STRAATNM,,SUBADRESID,SUBADRESID,,SUBADRES,SUBADRES,,SUBADR_BEGINDATUM,SUBADR_BEG,,SUBADR_TIJD,SUBADR_TIJ,,AARDSUBADRES,AARDSUBADR,,AARD,AARDADRPOS,,OG_COORD_X,X,,OG_COORD_Y,Y,,SUBADR_EINDDATUM,SUBADR_EIN,,HUISNR_EINDDATUM,HUISNR_EIN,,Gemeente,GEMNM,,StraatCode,STRAATCO,
    -> CRABadrID
CRABadrID: Counter
    SCOPE = Local
    CNT_ATTR = CRABadrID
    DOMAIN = counter
    START = 1
    -> 000_CRAB_alladr (writer SHAPE_1)
    -> 000_CRAB_alladr (writer FFS_1)
Note: 000_alladres_CRAB: 000 [SHAPE] / Alle actuele CRAB-adressen op toestand [Toestand]
000_CRAB_alladr (writer SHAPE_1)
    attributes: CRABadrID char(10), STRAATNMID number(11,0), STRAATNM char(254), HUISNRID number(11,0), HUISNR char(10), HUISNR_BEG char(20), HUISNR_TIJ char(20), HUISNR_EIN char(20), SUBADRESID number(11,0), SUBADRES char(254), SUBADR_BEG char(20), AARDSUBADR number(11,0), NISGEMCODE char(5), PKANCODE number(11,0), GEMNM char(4), AARDADRPOS number(11,0), X number(31,15), Y number(31,15), SUBADR_TIJ char(20), SUBADR_EIN char(20)
000_CRAB_alladr (writer FFS_1)
    attributes: CRABadrID varchar(10), STRAATNMID number(11,0), STRAATNM varchar(255), HUISNRID number(11,0), HUISNR varchar(10), HUISNR_BEG varchar(20), HUISNR_TIJ varchar(20), HUISNR_EIN varchar(20), SUBADRESID number(11,0), SUBADRES varchar(255), SUBADR_BEG varchar(20), AARDSUBADR number(11,0), NISGEMCODE varchar(5), PKANCODE number(11,0), GEMNM varchar(4), AARDADRPOS number(11,0), X number(31,15), Y number(31,15), SUBADR_TIJ varchar(20), SUBADR_EIN varchar(20)
TestFilter_5__Unfiltered_: Inspector
AttributeExposer
    ATTR_LIST = fme_basename,fme_dataset,fme_feature_type
    -> AttributeRemover
AttributeRemover
    REMOVE_ATTRS = fme_dataset,fme_basename,fme_feature_type

Bookmark: Input: CRAB tabellen db ORBIT
huisnummer (reader CSV_1)
    attributes: ID number(7,0), HUISNUMMERID number(8,0), STRAATNAAMID number(7,0), HUISNUMMER char(5), BEGINDATUM number(20,5), EINDDATUM number(20,5), TIJD number(20,5), ORGANISATIE number(2,0), BEWERKING number(2,0)
    -> DateFormatter_2
subadres (reader CSV_2)
    attributes: ID number(6,0), SUBADRESID number(8,0), HUISNUMMERID number(8,0), SUBADRES char(5), AARDSUBADRES number(2,0), BEGINDATUM number(20,5), EINDDATUM number(20,5), TIJD number(20,5), ORGANISATIE number(2,0), BEWERKING number(2,0)
    -> DateFormatter_2
adrespositie (reader CSV_3)
    attributes: ID number(8,0), ADRESID number(8,0), AARD number(2,0), OG_COORD_X number(17,9), OG_COORD_Y number(17,9), HERKOMST number(2,0), BEGINDATUM number(20,5), EINDDATUM number(20,5), TIJD number(20,5), ORGANISATIE number(2,0), BEWERKING number(2,0), SSMA_TimeStamp number(31,15)
    -> TestFilter_4
straatnaam (reader CSV_4)
    attributes: ID number(5,0), STRAATNAAMID number(7,0), STRAATCODE number(7,0), NISGEMEENTECODE number(6,0), STRAATNAAM char(32), TAALCODESTRAATNAAM char(3), STRAATNAAM2 char(1), TAALCODESTRAATNAAM2 char(1), BEGINDATUM number(20,5), EINDDATUM char(1), TIJD number(20,5), ORGANISATIE number(2,0), BEWERKING number(2,0)
    -> DateFormatter_2
postkantoncode (reader CSV_5)
    attributes: ID number(7,0), HUISNUMMERID number(8,0), POSTKANTONCODE number(5,0), BEGINDATUM number(20,5), EINDDATUM char(1), TIJD number(20,5), ORGANISATIE number(2,0), BEWERKING number(2,0)
    -> DateFormatter_2
