FME workspace 003_BEW_Wooneenheden.fmw
Title: 003_BEW_Wooneenheden.fmw
Description: Bewerkingen: 
Berekening van huishoudens en wooneenheden op basis van type woning (kadaster), bevolking en adreslocaties .
History: 2016-10-06,Jonas Verstraete,Initial Version,2016-10-21,Jonas Verstraete,Update to new cadastre datastructure

Parameters:
- MINX =   # Minimum X
- MINY =   # Minimum Y
- MAXX =   # Maximum X
- MAXY =   # Maximum Y
- SourceDataset_FFS_4 = ..\data\intermediate\002\002_CRAB_alladr_capakey.ffs   # Source FME Feature Store (FFS) File(s)
- SourceDataset_FFS_5 = ..\data\intermediate\001\001_BevReg_CRAB.ffs   # Source FME Feature Store (FFS) File(s)
- DestDataset_FFS = ..\data\intermediate\003\003_Huishoudens.ffs   # Destination FME Feature Store (FFS) File
- DestDataset_FFS_2 = ..\data\intermediate\003\003_Gebouweenheden_Adressen.ffs   # Destination FME Feature Store (FFS) File
- DestDataset_FFS_3 = ..\data\intermediate\003\003_KADparcel_Gebouweenheden.ffs   # Destination FME Feature Store (FFS) File
- DestDataset_ESRISHAPE = ..\data\intermediate\003   # Destination Esri Shapefile Folder
- SourceDataset_FFS = ..\data\intermediate\000\000_KAD.ffs   # Source FME Feature Store (FFS) File(s)
- SourceDataset_Handelspanden = ..\data\input\Handelspanden.shp   # Source Esri Shapefile(s)

Readers:
- FFS_1: FFS from $(SourceDataset_FFS_4) in EPSG:31370
- FFS_2: FFS from $(SourceDataset_FFS_5) in EPSG:31370
- FFS_3: FFS from $(SourceDataset_FFS) in EPSG:31370

Writers:
- FFS_4: FFS to $(DestDataset_FFS)
- FFS_5: FFS to $(DestDataset_FFS_2)
- FFS_6: FFS to $(DestDataset_FFS_3)
- ESRISHAPE_1: ESRISHAPE to $(DestDataset_ESRISHAPE)

Note: 003_BEW_Wooneenheden.fmw / Bewerkingen: / Berekening van huishoudens en wooneenheden op basis van type woning (kadaster), bevolking en adreslocaties .
GeometryExtractor
    OGCVERSION = 1.1
    REMOVE_GEOMETRY = No
    KIND_LONG = OGC Well Known Text
    OGC_WKT_PRECISION_DISPLAY = Shortened 64-bit
    ATTR = _geometry
    -> AttributeCreator_18
Note: Gebouwtype Andere / MET housingunits
TestFilter_16
    DEFAULT_VALUE = <UNFILTERED>
    TEST_LIST = BOOL_OP,OR,COMPOSITE_TEST,<Unused>,TEST_CLAUSE,"TEST @Value(housingUnitNumber) > 0",@Value(housingUnitNumber) > 0
    @Value(housingUnitNumber) > 0 -> TestFilter_17
    <UNFILTERED> -> Aggregator_6
Note: Meerdere verblijfseigendommen / per perceel mogelijk
TestFilter_17
    DEFAULT_VALUE = <UNFILTERED>
    TEST_LIST:
      BOOL_OP,OR,COMPOSITE_TEST,<Unused>,TEST_CLAUSE,"TEST @Value(constructionIndication) = 100
      TEST @Value(constructionIndication) = 110",Building
    Building -> PassThrough_2
    <UNFILTERED> -> Aggregator_6
Note: 1 verblijfseigendom per perceel
PassThrough_2: Tester
    TEST_MODE = Automatic
    TEST_DESCRIPTION = ""
    TEST_CLAUSE = TEST 0 = 0
    BOOL_OP = OR
    PASSED -> Aggregator_6
    PASSED -> TestFilter_18 [off]
Note: Create _eigendomList
Aggregator_6
    SEP = ;
    ACCUM_ATTRS_NAME = Yes
    LIST_NAME = _kadList
    SUM = housingUnitNumber
    MODE = Attributes Only
    ORDERED = No
    CONCAT_ATTRS = constructionType constructionIndication descriptPrivate nature
    GROUP_BY = capakey
    AGGREGATE -> GeometryReplacer
GeometryReplacer
    KIND_LONG = OGC Well Known Text
    SOURCE = @Value(_geometry)
    REMOVE_ATTRIBUTE = Yes
    OGC_WKT_PRECISION_DISPLAY = 64-bit
    -> AttributeKeeper_7
AttributeKeeper_7
    KEEP_ATTRS = constructionType,constructionIndication,housingUnitNumber,capakey,descriptPrivate,nature
    KEEP_LIST = _kadList{}.GebouwType _kadList{}._handhuiscorr _kadList{}._number_nr _kadList{}.aard _kadList{}.bathroomNumber _kadList{}.bisNumber _kadList{}.block _kadList{}.bouwjaar _kadList{}.builtSurface _kadList{}.cadastralIncome _kadList{}.cadastralIncomePerSurface _kadList{}.cadastralIncomePerSurfaceOtherDi _kadList{}.capakey _kadList{}.centralHeating _kadList{}.charCadastralIncome _kadList{}.constructionIndication _kadList{}.constructionQuality _kadList{}.constructionType _kadList{}.constructionYear _kadList{}.crossDetail _kadList{}.dateEndExoneration _kadList{}.dateSituation _kadList{}.decrete _kadList{}.descriptPrivate _kadList{}.divCad _kadList{}.exponentLetter _kadList{}.exponentNumber _kadList{}.floor _kadList{}.floorNumberAboveground _kadList{}.floorSituation _kadList{}.garageNumber _kadList{}.garret _kadList{}.housingUnitNumber _kadList{}.matUtil _kadList{}.nature _kadList{}.nisCom _kadList{}.notTaxedMatUtil _kadList{}.number _kadList{}.numberCadastralIncome _kadList{}.order _kadList{}.partNumber _kadList{}.physModYear _kadList{}.placeNumber _kadList{}.polWa _kadList{}.primaryNumber _kadList{}.propertySituationIdf _kadList{}.section _kadList{}.soilIndex _kadList{}.soilRent _kadList{}.street_code _kadList{}.street_situation _kadList{}.street_translation _kadList{}.surfaceNotTaxable _kadList{}.surfaceTaxable _kadList{}.surfaceVerif _kadList{}.usedSurface
    -> FeatureMerger_5 [REQUESTOR]
AttributeRenamer_2
    ATTR_TABLE = RENAME_SET_DEFAULT CAPAKEY > capakey
    -> AttributeKeeper
    -> FeatureMerger_6 [SUPPLIER]
AttributeKeeper
    KEEP_ATTRS = capakey,CRABadrID
    -> FeatureMerger [SUPPLIER]
Note: Add CAPAKEY
FeatureMerger
    ATTR_CONFLICT_RES = Use Requestor
    MERGE_TYPE = Attributes Only
    GEOM_TYPE = Build Polygons
    CONNECT_Z_MODE = First Wins
    ATTR_ACCUM_MODE = Merge Supplier
    PROCESS_DUPS = Yes
    IGNORE_NULLS = No
    JOIN_KEYS = @Value(CRABadrID) @Value(CRABadrID) AUTO
    SUPPLIERS_FIRST = No
    MERGED -> GeometryExtractor_2
    NOT_MERGED -> ERROR_not_merged_CRAB_CAPAKEY
GeometryExtractor_2
    OGCVERSION = 1.1
    REMOVE_GEOMETRY = No
    KIND_LONG = OGC Well Known Text
    OGC_WKT_PRECISION_DISPLAY = Shortened 64-bit
    ATTR = _geometry
    -> TestFilter
Note: Create _huishoudList / Wooneenh-niveau
Aggregator_4
    SEP = ,
    AGGREGATE_TYPE = Homogeneous Collection (If Possible)
    ACCUM_ATTRS_NAME = Yes
    LIST_NAME = _huishoudList
    SUM = ParticHh MeerprsHh EenprsHh
    MODE = Geometry - Assemble One Level
    ORDERED = No
    GROUP_BY = CRABadrID capakey
    AGGREGATE -> AttributeRemover
Note: Create _huishoudList / Wooneenh-niveau
Aggregator_5
    SEP = ,
    AGGREGATE_TYPE = Homogeneous Collection (If Possible)
    ACCUM_ATTRS_NAME = Yes
    LIST_NAME = _huishoudList
    SUM = GemeensHh
    MODE = Geometry - Assemble One Level
    ORDERED = No
    GROUP_BY = CRABadrID capakey
    AGGREGATE -> AttributeRemover
AttributeRemover
    REMOVE_ATTRS = GEBDAT,AANTKIND,GEZINSGROOTTE,REFPERS,REGISTER,HuishType,BevRegID,NAT_OUD,BURGSTAAT,GESLACHT,HuishGrootte,VERWERVING,NATIONALITEIT
    LIST_ATTRS = _huishoudList{}._geometry
    -> GeometryReplacer_2
GeometryReplacer_2
    KIND_LONG = OGC Well Known Text
    SOURCE = @Value(_geometry)
    REMOVE_ATTRIBUTE = Yes
    OGC_WKT_PRECISION_DISPLAY = 64-bit
    -> AttributeKeeper_3
Note: HuishoudInfo op Wooneenh-niveau
AttributeKeeper_3
    KEEP_ATTRS = GEMNM,SUBADRES,EenprsHh,MeerprsHh,PKANCODE,ParticHh,HUISNR,CRABadrID,GemeensHh,STRAATNM,capakey
    KEEP_LIST = _huishoudList{}.AANTKIND _huishoudList{}.BURGSTAAT _huishoudList{}.BevRegID _huishoudList{}.GEBDAT _huishoudList{}.GESLACHT _huishoudList{}.GEZINSGROOTTE _huishoudList{}.HuishGrootte _huishoudList{}.HuishType _huishoudList{}.NATIONALITEIT _huishoudList{}.NAT_OUD _huishoudList{}.REFPERS _huishoudList{}.REGISTER _huishoudList{}.VERWERVING
    -> FeatureMerger_6 [REQUESTOR]
    -> AttributeCreator_35
Note: Functie: andere
AttributeCreator_27
    ATTR_TABLE = SET_TO Functie = andere
    -> AttributeKeeper_8
AttributeCreator_35
    ATTR_TABLE = SET_TO Domicilie = met domicilie
    -> FeatureMerger_7 [REQUESTOR]
Junction
    -> 003_Huishoudens (writer FFS_4)
    -> AttributeRenamer_5
AttributeRenamer_5
    ATTR_TABLE:
      RENAME_SET_DEFAULT NATIONALITEIT > NATIONALIT
      RENAME_SET_DEFAULT GEZINSGROOTTE > GEZINSGROO
      RENAME_SET_DEFAULT HuishGrootte > HuishGroot
    -> 003_Huishoudens (writer ESRISHAPE_1)
PassThrough_Particuliere: Tester
    TEST_MODE = Automatic
    TEST_DESCRIPTION = ""
    TEST_CLAUSE = TEST 0 = 0
    BOOL_OP = OR
    PASSED -> FeatureMerger_3 [SUPPLIER]
    PASSED -> TestFilter_3
PassThrough_Gemeensch: Tester
    TEST_MODE = Automatic
    TEST_DESCRIPTION = ""
    TEST_CLAUSE = TEST 0 = 0
    BOOL_OP = OR
    PASSED -> TestFilter_12
    PASSED -> TestFilter_13
    PASSED -> FeatureMerger_3 [REQUESTOR]
ERROR_not_merged_CRAB_CAPAKEY: Inspector
Note: Adresniveau: Create inwList
Aggregator_8
    SEP = ,
    AGGREGATE_TYPE = Homogeneous Collection (If Possible)
    ACCUM_ATTRS_NAME = Yes
    LIST_NAME = _inwList
    MODE = Geometry - Assemble One Level
    ORDERED = No
    GROUP_BY = CRABadrID
    AGGREGATE -> AttributeKeeper_11
AttributeKeeper_11
    KEEP_ATTRS = CRABadrID
    KEEP_LIST = _inwList{}.AANTKIND _inwList{}.BURGSTAAT _inwList{}.BevRegID _inwList{}.CRAB_merge _inwList{}.CRABadrID _inwList{}.GEBDAT _inwList{}.GEMNM _inwList{}.GESLACHT _inwList{}.GEZINSGROOTTE _inwList{}.INDEX _inwList{}.NATIONALITEIT _inwList{}.NAT_OUD _inwList{}.NUMMER _inwList{}.PKANCODE _inwList{}.REFPERS _inwList{}.REGISTER _inwList{}.STRAATKODE _inwList{}.VERWERVING _inwList{}.gemeensch _inwList{}.sector _inwList{}.stadsdeel _inwList{}.wijknaam
    -> FeatureMerger_8 [SUPPLIER]
PassThrough_10: Tester
    TEST_MODE = Automatic
    TEST_DESCRIPTION = ""
    TEST_CLAUSE = TEST 0 = 0
    BOOL_OP = OR
    PASSED -> ListAttributeCreator_3
Junction_2
    -> AttributeCreator_43
Note: Functie: woning
AttributeCreator_34
    ATTR_TABLE = SET_TO Functie = woning
    -> AttributeExposer_6
AttributeExposer_6
    ATTR_LIST = _bothfirst{}.Functie,_bothsecond{}.HandelID
    -> AttributeKeeper_8
AttributeKeeper_8
    KEEP_ATTRS = Domicilie,_handel.CRABadrID,Wooneenh,Gebouweenh,capakey,Functie,GebouwType
    KEEP_LIST = _bothfirst{}.CRABadrID _bothfirst{}.Functie _bothsecond{}.HandelID _kadList{}.GebouwType _kadList{}.aard _kadList{}.bathroomNumber _kadList{}.bisNumber _kadList{}.block _kadList{}.bouwjaar _kadList{}.builtSurface _kadList{}.cadastralIncome _kadList{}.cadastralIncomePerSurface _kadList{}.cadastralIncomePerSurfaceOtherDi _kadList{}.capakey _kadList{}.centralHeating _kadList{}.charCadastralIncome _kadList{}.constructionIndication _kadList{}.constructionQuality _kadList{}.constructionType _kadList{}.constructionYear _kadList{}.crossDetail _kadList{}.dateEndExoneration _kadList{}.decrete _kadList{}.descriptPrivate _kadList{}.divCad _kadList{}.exponentLetter _kadList{}.exponentNumber _kadList{}.floor _kadList{}.floorNumberAboveground _kadList{}.floorSituation _kadList{}.garageNumber _kadList{}.garret _kadList{}.housingUnitNumber _kadList{}.matUtil _kadList{}.nature _kadList{}.notTaxedMatUtil _kadList{}.number _kadList{}.numberCadastralIncome _kadList{}.order _kadList{}.partNumber _kadList{}.physModYear _kadList{}.placeNumber _kadList{}.polWa _kadList{}.primaryNumber _kadList{}.propertySituationIdf _kadList{}.section _kadList{}.soilIndex _kadList{}.soilRent _kadList{}.street_situation _kadList{}.street_translation _kadList{}.surfaceNotTaxable _kadList{}.surfaceTaxable _kadList{}.surfaceVerif _kadList{}.usedSurface
    -> FeatureMerger_7 [SUPPLIER]
Note: Merge PERC KAD info to / gebouweenheden
FeatureMerger_7
    ATTR_CONFLICT_RES = Use Requestor
    MERGE_TYPE = Attributes Only
    ATTR_ACCUM_MODE = Merge Supplier
    PROCESS_DUPS = No
    IGNORE_NULLS = No
    JOIN_KEYS = @Value(capakey) @Value(capakey) AUTO
    SUPPLIERS_FIRST = No
    MERGED -> TestFilter_29
    NOT_MERGED -> AttributeCreator_36
TestFilter_29
    DEFAULT_VALUE = <UNFILTERED>
    TEST_LIST:
      BOOL_OP,OR,COMPOSITE_TEST,<Unused>,TEST_CLAUSE,"TEST @Value(CRABadrID) = @Value(_handel.CRABadrID)
      TEST @Value(CRABadrID) IN @Value(_handel.CRABadrID)",handhuis
    handhuis -> VariableRetriever_2
    <UNFILTERED> -> AttributeCreator_6
AttributeCreator_6
    ATTR_TABLE = SET_TO TypeEenh = Gebouweenheid
    -> FeatureMerger_8 [REQUESTOR]
Note: Eenheid op openbaar domein
AttributeCreator_36
    ATTR_TABLE = SET_TO TypeEenh = Eenheid op openbaar domein
    -> AttributeCreator_44
Note: Functie / if met domicilie: woning / else: andere
AttributeCreator_44
    ATTR_TABLE = SET_TO Functie = FME_CONDITIONAL:DEFAULT_VALUE'andere'BOOL_OP;OR;COMPOSITE_TEST;<Unused>;TEST @Value(Domicilie) = met domicilie'woning'FME_NUM_CONDITIONS2___
    -> FeatureMerger_8 [REQUESTOR]
FeatureMerger_8
    ATTR_CONFLICT_RES = Use Requestor
    MERGE_TYPE = Attributes Only
    ATTR_ACCUM_MODE = Merge Supplier
    PROCESS_DUPS = No
    IGNORE_NULLS = No
    JOIN_KEYS = @Value(CRABadrID) @Value(CRABadrID) AUTO
    SUPPLIERS_FIRST = No
    MERGED -> AttributeKeeper_12
    NOT_MERGED -> AttributeKeeper_12
Note: Output Gebouweenheden / + eenheden openbaar domein (adresposities)
AttributeKeeper_12
    KEEP_ATTRS = NISGEMCODE,GebouwType,HUISNR,SUBADR_TIJ,TypeEenh,Wooneenh,MeerprsHh,X,Y,Gebouweenh,EenprsHh,SUBADRES,PKANCODE,CRABadrID,ParticHh,GEMNM,capakey,SUBADR_BEG,AARDSUBADR,Functie,STRAATNMID,SUBADRESID,GemeensHh,SUBADR_EIN,HUISNR_EIN,HandelID,Domicilie,AARDADRPOS,STRAATNM,HUISNRID,HUISNR_BEG,HUISNR_TIJ
    KEEP_LIST = _huishoudList{}.AANTKIND _huishoudList{}.BURGSTAAT _huishoudList{}.BevRegID _huishoudList{}.GEBDAT _huishoudList{}.GESLACHT _huishoudList{}.GEZINSGROOTTE _huishoudList{}.HuishGrootte _huishoudList{}.HuishType _huishoudList{}.NATIONALITEIT _huishoudList{}.NAT_OUD _huishoudList{}.REFPERS _huishoudList{}.REGISTER _huishoudList{}.VERWERVING _inwList{}.AANTKIND _inwList{}.BURGSTAAT _inwList{}.BevRegID _inwList{}.CRAB_merge _inwList{}.CRABadrID _inwList{}.GEBDAT _inwList{}.GEMNM _inwList{}.GESLACHT _inwList{}.GEZINSGROOTTE _inwList{}.INDEX _inwList{}.NATIONALITEIT _inwList{}.NAT_OUD _inwList{}.NUMMER _inwList{}.PKANCODE _inwList{}.REFPERS _inwList{}.REGISTER _inwList{}.STRAATKODE _inwList{}.VERWERVING _inwList{}.gemeensch _inwList{}.sector _inwList{}.stadsdeel _inwList{}.wijknaam
    -> AttributeKeeper_13
    -> 003_Gebouweenheden_Adressen (writer FFS_5)
AttributeKeeper_13
    KEEP_ATTRS = NISGEMCODE,GebouwType,HUISNR,SUBADR_TIJ,TypeEenh,Wooneenh,MeerprsHh,X,Y,EenprsHh,SUBADRES,PKANCODE,CRABadrID,ParticHh,GEMNM,capakey,SUBADR_BEG,AARDSUBADR,Functie,STRAATNMID,SUBADRESID,GemeensHh,SUBADR_EIN,HUISNR_EIN,HandelID,Domicilie,AARDADRPOS,STRAATNM,HUISNRID,HUISNR_BEG,HUISNR_TIJ
    -> Aggregator_9
Aggregator_9
    SEP = ,
    AGGREGATE_TYPE = Homogeneous Collection (If Possible)
    ACCUM_ATTRS_NAME = Yes
    LIST_NAME = _gebouweenhList
    MODE = Geometry - Assemble One Level
    ORDERED = No
    GROUP_BY = capakey
    AGGREGATE -> AttributeKeeper_14
AttributeKeeper_14
    KEEP_ATTRS = capakey
    KEEP_LIST = _gebouweenhList{}.AARDADRPOS _gebouweenhList{}.AARDSUBADR _gebouweenhList{}.CRABadrID _gebouweenhList{}.Domicilie _gebouweenhList{}.EenprsHh _gebouweenhList{}.Functie _gebouweenhList{}.GEMNM _gebouweenhList{}.GebouwType _gebouweenhList{}.GemeensHh _gebouweenhList{}.HUISNR _gebouweenhList{}.HUISNRID _gebouweenhList{}.HUISNR_BEG _gebouweenhList{}.HUISNR_EIN _gebouweenhList{}.HUISNR_TIJ _gebouweenhList{}.HandelID _gebouweenhList{}.MeerprsHh _gebouweenhList{}.NISGEMCODE _gebouweenhList{}.PKANCODE _gebouweenhList{}.ParticHh _gebouweenhList{}.STRAATNM _gebouweenhList{}.STRAATNMID _gebouweenhList{}.SUBADRES _gebouweenhList{}.SUBADRESID _gebouweenhList{}.SUBADR_BEG _gebouweenhList{}.SUBADR_EIN _gebouweenhList{}.SUBADR_TIJ _gebouweenhList{}.TypeEenh _gebouweenhList{}.Wooneenh _gebouweenhList{}.X _gebouweenhList{}.Y
    -> FeatureMerger_9 [SUPPLIER]

Bookmark: Input KAD_parcel
000_KAD_parcel (reader FFS_3)
    attributes: propertySituationIdf number(8,0), divCad number(5,0), section varchar(1), primaryNumber number(4,0), bisNumber number(2,0), exponentLetter varchar(1), exponentNumber number(3,0), partNumber varchar(5), capakey varchar(17), order varchar(4), nature varchar(3), descriptPrivate varchar(35), block varchar(2), floor varchar(2), floorSituation varchar(5), crossDetail varchar(20), matUtil varchar(1), notTaxedMatUtil varchar(3), nisCom varchar(6), street_situation varchar(20), street_translation varchar(1), street_code varchar(6), number varchar(6), polWa varchar(8), surfaceNotTaxable number(10,0), surfaceTaxable number(10,0), surfaceVerif varchar(2), constructionYear number(5,0), soilIndex number(2,0), soilRent varchar(2),
      cadastralIncomePerSurface number(3,0), cadastralIncomePerSurfaceOtherDi number(2,0), numberCadastralIncome number(1,0), charCadastralIncome varchar(1), cadastralIncome number(8,0), dateEndExoneration varchar(1), decrete varchar(1), constructionIndication number(4,0), constructionType varchar(2), floorNumberAboveground number(2,0), garret number(2,0), physModYear number(5,0), constructionQuality varchar(2), garageNumber number(3,0), centralHeating number(3,0), bathroomNumber number(3,0), housingUnitNumber number(2,0), placeNumber number(4,0), builtSurface number(5,0), usedSurface number(5,0), dateSituation varchar(9), aard varchar(10), bouwjaar varchar(25)
    -> GeometryExtractor
    -> AttributeCreator_5 [off]
    -> FeatureMerger_2 [REQUESTOR] [off]

Bookmark: LGGR_GebouwType
AttributeCreator_5
    ATTR_TABLE = SET_TO constructionIndication = FME_CONDITIONAL:DEFAULT_VALUE'@PadLeft(@Value(constructionIndication),3,0)'BOOL_OP;OR;COMPOSITE_TEST;<Unused>;TEST constructionIndication ATTRIBUTE_VALUE_NULL _FME_BLANK_STRING_;TEST constructionIndication ATTRIBUTE_IS_EMPTY _FME_BLANK_STRING_;TEST constructionIndication ATTRIBUTE_IS_MISSING _FME_BLANK_STRING_'_FME_NO_OP_'FME_NUM_CONDITIONS2___
    -> TestFilter_4
Note: Select woningen
TestFilter_4
    DEFAULT_VALUE = Andere
    TEST_LIST:
      BOOL_OP,COMPOSITE,COMPOSITE_TEST,"""(1 OR 2 OR 3 OR 4 OR 5 OR 6 OR 7 OR 8 OR 9 OR 10 OR 11) AND 12""",TEST_CLAUSE,"TEST @Value(constructionIndication) LIKE %010%
      TEST @Value(constructionIndication) LIKE %030%
      TEST @Value(constructionIndication) LIKE %031%
      TEST @Value(constructionIndication) LIKE %032%
      TEST @Value(constructionIndication) LIKE %033%
      TEST @Value(constructionIndication) LIKE %040%
      TEST @Value(constructionIndication) LIKE %041%
      TEST @Value(constructionIndication) LIKE %050%
      TEST @Value(constructionIndication) LIKE %060%
      TEST @Value(constructionIndication) LIKE %070%
      TEST @Value(constructionIndication) LIKE %080%
      TEST @Value(constructionType) LIKE %A%",Huis in gesloten bebouwing,BOOL_OP,COMPOSITE,COMPOSITE_TEST,"""(1 OR 2 OR 3 OR 4 OR 5 OR 6 OR 7 OR 8 OR 9 OR 10 OR 11) AND 12""",TEST_CLAUSE,"TEST @Value(constructionIndication) LIKE %010%
      TEST @Value(constructionIndication) LIKE %030%
      TEST @Value(constructionIndication) LIKE %031%
      TEST @Value(constructionIndication) LIKE %032%
      TEST @Value(constructionIndication) LIKE %033%
      TEST @Value(constructionIndication) LIKE %040%
      TEST @Value(constructionIndication) LIKE %041%
      TEST @Value(constructionIndication) LIKE %050%
      TEST @Value(constructionIndication) LIKE %060%
      TEST @Value(constructionIndication) LIKE %070%
      TEST @Value(constructionIndication) LIKE %080%
      TEST @Value(constructionType) LIKE %B%",Huis in half open bebouwing,BOOL_OP,COMPOSITE,COMPOSITE_TEST,"""(1 OR 2 OR 3 OR 4 OR 5 OR 6 OR 7 OR 8 OR 9 OR 10 OR 11 OR 12 OR 13) AND 14""",TEST_CLAUSE,"TEST @Value(constructionIndication) LIKE %010%
      TEST @Value(constructionIndication) LIKE %030%
      TEST @Value(constructionIndication) LIKE %031%
      TEST @Value(constructionIndication) LIKE %032%
      TEST @Value(constructionIndication) LIKE %033%
      TEST @Value(constructionIndication) LIKE %040%
      TEST @Value(constructionIndication) LIKE %041%
      TEST @Value(constructionIndication) LIKE %050%
      TEST @Value(constructionIndication) LIKE %060%
      TEST @Value(constructionIndication) LIKE %070%
      TEST @Value(constructionIndication) LIKE %080%
      TEST @Value(constructionIndication) LIKE %020%
      TEST @Value(constructionIndication) LIKE %470%
      TEST @Value(constructionType) LIKE %C%",Huis in open bebouwing, hoeve of kasteel,BOOL_OP,OR,COMPOSITE_TEST,<Unused>,TEST_CLAUSE,"TEST @Value(constructionIndication) LIKE %100%
      TEST @Value(constructionIndication) LIKE %101%
      TEST @Value(constructionIndication) LIKE %104%
      TEST @Value(constructionIndication) LIKE %105%
      TEST @Value(constructionIndication) LIKE %110%
      TEST @Value(constructionIndication) LIKE %111%
      TEST @Value(constructionIndication) LIKE %114%
      TEST @Value(constructionIndication) LIKE %115%
      TEST @Value(constructionIndication) LIKE %999%",Buildings en flatgebouwen met appartementen,BOOL_OP,OR,COMPOSITE_TEST,<Unused>,TEST_CLAUSE,"TEST @Value(constructionIndication) LIKE %200%
      TEST @Value(constructionIndication) LIKE %210%
      TEST @Value(constructionIndication) LIKE %220%
      TEST @Value(constructionIndication) LIKE %230%",Handelshuis
    Huis in gesloten bebouwing -> AttributeCreator
    Huis in half open bebouwing -> AttributeCreator_2
    Huis in open bebouwing, hoeve of kasteel -> AttributeCreator_3
    Buildings en flatgebouwen met appartementen -> AttributeCreator_4
    Handelshuis -> AttributeCreator_20
    Andere -> AttributeCreator_28
AttributeCreator
    ATTR_LIST = GebouwType,Huizen in gesloten bebouwing
    -> PassThrough
    -> TestFilter_7
    -> DuplicateFilter_3
AttributeCreator_2
    ATTR_LIST = GebouwType,Huizen in half open bebouwing
    -> PassThrough
    -> TestFilter_8
    -> DuplicateFilter_3
AttributeCreator_3
    ATTR_LIST = GebouwType,Huizen in open bebouwing, hoeven en kastelen
    -> PassThrough
    -> TestFilter_9
    -> DuplicateFilter_3
AttributeCreator_4
    ATTR_LIST = GebouwType,Buildings en flatgebouwen met appartementen
    -> PassThrough
    -> TestFilter_10
AttributeCreator_20
    ATTR_LIST = GebouwType,Handelshuizen
    -> PassThrough
    -> AttributeCreator_20_Output
    -> DuplicateFilter_3
AttributeCreator_28
    ATTR_LIST = GebouwType,Andere
    -> PassThrough
    -> TestFilter_6

Bookmark: Testen uitzonderingen KAD data
TestFilter_7
    DEFAULT_VALUE = <UNFILTERED>
    TEST_LIST = BOOL_OP,OR,COMPOSITE_TEST,<Unused>,TEST_CLAUSE,"TEST @Value(housingUnitNumber) > 1",@Value(housingUnitNumber) > 1
    @Value(housingUnitNumber) > 1 -> TestFilter_7__Value_housingUnitNumber____1
    <UNFILTERED> -> TestFilter_7__Unfiltered_
TestFilter_7__Value_housingUnitNumber____1: Inspector
TestFilter_7__Unfiltered_: Inspector
TestFilter_8
    DEFAULT_VALUE = <UNFILTERED>
    TEST_LIST = BOOL_OP,OR,COMPOSITE_TEST,<Unused>,TEST_CLAUSE,"TEST @Value(housingUnitNumber) > 1",@Value(housingUnitNumber) > 1
    @Value(housingUnitNumber) > 1 -> TestFilter_8__Value_housingUnitNumber____1
    <UNFILTERED> -> TestFilter_8__Unfiltered_
TestFilter_8__Value_housingUnitNumber____1: Inspector
TestFilter_8__Unfiltered_: Inspector
TestFilter_9
    DEFAULT_VALUE = <UNFILTERED>
    TEST_LIST = BOOL_OP,OR,COMPOSITE_TEST,<Unused>,TEST_CLAUSE,"TEST @Value(housingUnitNumber) > 1",@Value(housingUnitNumber) > 1
    @Value(housingUnitNumber) > 1 -> TestFilter_9__Value_housingUnitNumber____1
    <UNFILTERED> -> TestFilter_9__Unfiltered_
TestFilter_9__Value_housingUnitNumber____1: Inspector
TestFilter_9__Unfiltered_: Inspector
TestFilter_10
    DEFAULT_VALUE = <UNFILTERED>
    TEST_LIST:
      BOOL_OP,OR,COMPOSITE_TEST,<Unused>,TEST_CLAUSE,"TEST @Value(constructionIndication) = 100
      TEST @Value(constructionIndication) = 110",Building
    Building -> DuplicateFilter_2
    <UNFILTERED> -> TestFilter_10__Unfiltered_
    <UNFILTERED> -> Aggregator
DuplicateFilter_2
    INPUT_ORDERED_CHOICE = No
    KEYATTR = capakey
    UNIQUE -> DuplicateFilter_2_Unique
    DUPLICATE -> DuplicateFilter_2_Duplicate
DuplicateFilter_2_Unique: Inspector
DuplicateFilter_2_Duplicate: Inspector
Note: Create _eigendomList
Aggregator
    SEP = ,
    AGGREGATE_TYPE = Homogeneous Collection (If Possible)
    ACCUM_ATTRS_NAME = No
    LIST_NAME = _kadList
    SUM = housingUnitNumber
    MODE = Geometry - Assemble One Level
    ORDERED = No
    GROUP_BY = capakey
TestFilter_10__Unfiltered_: Inspector
Note: Test meerdere eigendommen op perceel als (handels)huis / Fout in data: enkel eerste wordt gebruikt
DuplicateFilter_3
    INPUT_ORDERED_CHOICE = No
    KEYATTR = capakey
    UNIQUE -> DuplicateFilter_3_Unique
    DUPLICATE -> DuplicateFilter_3_Duplicate
DuplicateFilter_3_Unique: Inspector
DuplicateFilter_3_Duplicate: Inspector
AttributeCreator_20_Output: Inspector
PassThrough: Tester
    TEST_MODE = Automatic
    TEST_DESCRIPTION = ""
    TEST_CLAUSE = TEST 0 = 0
    BOOL_OP = OR
    PASSED -> TestFilter_5
    FAILED -> PassThrough_Failed
TestFilter_5
    DEFAULT_VALUE = <UNFILTERED>
    TEST_LIST:
      BOOL_OP,AND,COMPOSITE_TEST,<Unused>,TEST_CLAUSE,"TEST @Value(GebouwType) = Andere
      TEST @Value(housingUnitNumber) > 0",@Value(GebouwType) = Andere
    @Value(GebouwType) = Andere -> TestFilter_5__Value_GebouwType____Andere
    <UNFILTERED> -> TestFilter_5__Unfiltered_
TestFilter_5__Value_GebouwType____Andere: Inspector
TestFilter_5__Unfiltered_: Inspector
PassThrough_Failed: Inspector
TestFilter_6
    DEFAULT_VALUE = <UNFILTERED>
    TEST_LIST = BOOL_OP,OR,COMPOSITE_TEST,<Unused>,TEST_CLAUSE,"TEST @Value(housingUnitNumber) > 0",@Value(housingUnitNumber) > 0
    @Value(housingUnitNumber) > 0 -> TestFilter_6__Value_housingUnitNumber____0
    <UNFILTERED> -> TestFilter_6__Unfiltered_
Note: NAKIJKEN / selectie 220 niet juist gemaakt?
TestFilter_6__Value_housingUnitNumber____0: Inspector
TestFilter_6__Unfiltered_: Inspector
TestFilter_18
    DEFAULT_VALUE = <UNFILTERED>
    TEST_LIST:
      BOOL_OP,OR,COMPOSITE_TEST,<Unused>,TEST_CLAUSE,"TEST @Value(housingUnitNumber) < 1
      TEST housingUnitNumber ATTRIBUTE_VALUE_NULL """"
      TEST housingUnitNumber ATTRIBUTE_IS_EMPTY """"
      TEST housingUnitNumber ATTRIBUTE_IS_MISSING """"",@Value(housingUnitNumber) < 1
    @Value(housingUnitNumber) < 1 -> TestFilter_18__Value_housingUnitNumber____1
    <UNFILTERED> -> TestFilter_18__Unfiltered_
TestFilter_18__Value_housingUnitNumber____1: Inspector
TestFilter_18__Unfiltered_: Inspector
Note: Test alle capakey's CRAB_capa (supplier) / merge KAD_parcel info (requestor) / zou niet meer mogen voorkomen (alle CAPA's mee in 000_KADbasisdata
FeatureMerger_2
    ATTR_CONFLICT_RES = Use Requestor
    MERGE_TYPE = Attributes Only
    GEOM_TYPE = Build Polygons
    CONNECT_Z_MODE = First Wins
    ATTR_ACCUM_MODE = Merge Supplier
    PROCESS_DUPS = Yes
    IGNORE_NULLS = No
    JOIN_KEYS = @Value(capakey) @Value(CAPAKEY) AUTO
    SUPPLIERS_FIRST = No
    MERGED -> FeatureMerger_2_Merged
    NOT_MERGED -> FeatureMerger_2_NotMerged
    REFERENCED -> FeatureMerger_2_Referenced
    UNREFERENCED -> FeatureMerger_2_Unreferenced
    DUPLICATE_SUPPLIER -> FeatureMerger_2_DuplicateSupplier
FeatureMerger_2_Merged: Inspector
FeatureMerger_2_NotMerged: Inspector
FeatureMerger_2_Referenced: Inspector
FeatureMerger_2_Unreferenced: Inspector
FeatureMerger_2_DuplicateSupplier: Inspector

Bookmark: LGGR_GebouwType
AttributeCreator_18
    ATTR_TABLE = SET_TO constructionIndication = FME_CONDITIONAL:DEFAULT_VALUE'@PadLeft(@Value(constructionIndication),3,0)'BOOL_OP;OR;COMPOSITE_TEST;<Unused>;TEST constructionIndication ATTRIBUTE_VALUE_NULL _FME_BLANK_STRING_;TEST constructionIndication ATTRIBUTE_IS_EMPTY _FME_BLANK_STRING_;TEST constructionIndication ATTRIBUTE_IS_MISSING _FME_BLANK_STRING_'_FME_NO_OP_'FME_NUM_CONDITIONS2___
    -> AttributeCreator_32
Note: attribuut voor latere / selectie handhuiscorrectie
Note: _number_nr / Om zelfde formaat als _handhuiscorr_nr / te hebben in ListComparer. / (bug in ListComparer intussen opgelost)
AttributeCreator_32
    ATTR_TABLE:
      SET_TO _handhuiscorr = FME_CONDITIONAL:DEFAULT_VALUE'_FME_NO_OP_'BOOL_OP;OR;COMPOSITE_TEST;<Unused>;TEST @Value(constructionIndication) = 200;TEST @Value(constructionIndication) = 210;TEST @Value(constructionIndication) = 220;TEST @Value(constructionIndication) = 230'handhuis'BOOL_OP;OR;COMPOSITE_TEST;<Unused>;TEST @Value(descriptPrivate) = HAND/HUIS'handhuis'BOOL_OP;OR;COMPOSITE_TEST;<Unused>;TEST @Value(nature) = 407'handhuis'FME_NUM_CONDITIONS4___
      SET_TO _number_nr = @Substring(@Value(number),0,@FindRegEx(@Value(number),[a-zA-Z]))
    -> TestFilter_15
Note: Select verblijfseigendommen
TestFilter_15
    DEFAULT_VALUE = Andere
    TEST_LIST:
      BOOL_OP,COMPOSITE,COMPOSITE_TEST,"""(1 OR 2 OR 3 OR 4 OR 5 OR 6 OR 7 OR 8 OR 9 OR 10 OR 11) AND 12""",TEST_CLAUSE,"TEST @Value(constructionIndication) LIKE %010%
      TEST @Value(constructionIndication) LIKE %030%
      TEST @Value(constructionIndication) LIKE %031%
      TEST @Value(constructionIndication) LIKE %032%
      TEST @Value(constructionIndication) LIKE %033%
      TEST @Value(constructionIndication) LIKE %040%
      TEST @Value(constructionIndication) LIKE %041%
      TEST @Value(constructionIndication) LIKE %050%
      TEST @Value(constructionIndication) LIKE %060%
      TEST @Value(constructionIndication) LIKE %070%
      TEST @Value(constructionIndication) LIKE %080%
      TEST @Value(constructionType) LIKE %A%",Huis in gesloten bebouwing,BOOL_OP,COMPOSITE,COMPOSITE_TEST,"""(1 OR 2 OR 3 OR 4 OR 5 OR 6 OR 7 OR 8 OR 9 OR 10 OR 11) AND 12""",TEST_CLAUSE,"TEST @Value(constructionIndication) LIKE %010%
      TEST @Value(constructionIndication) LIKE %030%
      TEST @Value(constructionIndication) LIKE %031%
      TEST @Value(constructionIndication) LIKE %032%
      TEST @Value(constructionIndication) LIKE %033%
      TEST @Value(constructionIndication) LIKE %040%
      TEST @Value(constructionIndication) LIKE %041%
      TEST @Value(constructionIndication) LIKE %050%
      TEST @Value(constructionIndication) LIKE %060%
      TEST @Value(constructionIndication) LIKE %070%
      TEST @Value(constructionIndication) LIKE %080%
      TEST @Value(constructionType) LIKE %B%",Huis in half open bebouwing,BOOL_OP,COMPOSITE,COMPOSITE_TEST,"""(1 OR 2 OR 3 OR 4 OR 5 OR 6 OR 7 OR 8 OR 9 OR 10 OR 11 OR 12 OR 13) AND 14""",TEST_CLAUSE,"TEST @Value(constructionIndication) LIKE %010%
      TEST @Value(constructionIndication) LIKE %030%
      TEST @Value(constructionIndication) LIKE %031%
      TEST @Value(constructionIndication) LIKE %032%
      TEST @Value(constructionIndication) LIKE %033%
      TEST @Value(constructionIndication) LIKE %040%
      TEST @Value(constructionIndication) LIKE %041%
      TEST @Value(constructionIndication) LIKE %050%
      TEST @Value(constructionIndication) LIKE %060%
      TEST @Value(constructionIndication) LIKE %070%
      TEST @Value(constructionIndication) LIKE %080%
      TEST @Value(constructionIndication) LIKE %020%
      TEST @Value(constructionIndication) LIKE %470%
      TEST @Value(constructionType) LIKE %C%",Huis in open bebouwing, hoeve of kasteel,BOOL_OP,OR,COMPOSITE_TEST,<Unused>,TEST_CLAUSE,"TEST @Value(constructionIndication) LIKE %100%
      TEST @Value(constructionIndication) LIKE %101%
      TEST @Value(constructionIndication) LIKE %104%
      TEST @Value(constructionIndication) LIKE %105%
      TEST @Value(constructionIndication) LIKE %110%
      TEST @Value(constructionIndication) LIKE %111%
      TEST @Value(constructionIndication) LIKE %114%
      TEST @Value(constructionIndication) LIKE %115%
      TEST @Value(constructionIndication) LIKE %999%",Buildings en flatgebouwen met appartementen,BOOL_OP,OR,COMPOSITE_TEST,<Unused>,TEST_CLAUSE,"TEST @Value(constructionIndication) LIKE %200%
      TEST @Value(constructionIndication) LIKE %210%
      TEST @Value(constructionIndication) LIKE %220%
      TEST @Value(constructionIndication) LIKE %230%",Handelshuis
    Huis in gesloten bebouwing -> AttributeCreator_12
    Huis in half open bebouwing -> AttributeCreator_13
    Huis in open bebouwing, hoeve of kasteel -> AttributeCreator_14
    Buildings en flatgebouwen met appartementen -> AttributeCreator_15
    Handelshuis -> AttributeCreator_16
    Andere -> AttributeCreator_17
AttributeCreator_12
    ATTR_LIST = GebouwType,Huizen in gesloten bebouwing
    -> PassThrough_2
AttributeCreator_13
    ATTR_LIST = GebouwType,Huizen in half open bebouwing
    -> PassThrough_2
AttributeCreator_14
    ATTR_LIST = GebouwType,Huizen in open bebouwing, hoeven en kastelen
    -> PassThrough_2
AttributeCreator_15
    ATTR_LIST = GebouwType,Buildings en flatgebouwen met appartementen
    -> TestFilter_17
AttributeCreator_16
    ATTR_LIST = GebouwType,Handelshuizen
    -> PassThrough_2
AttributeCreator_17
    ATTR_LIST = GebouwType,Andere
    -> TestFilter_16

Bookmark: Input CRAB_Capakey
002_CRAB_alladr_capakey (reader FFS_1)
    attributes: CRABadrID varchar(10), STRAATNMID number(11,0), STRAATNM varchar(255), HUISNRID number(11,0), HUISNR varchar(10), HUISNR_BEG varchar(20), HUISNR_TIJ varchar(20), HUISNR_EIN varchar(20), SUBADRESID number(11,0), SUBADRES varchar(255), SUBADR_BEG varchar(20), AARDSUBADR number(11,0), NISGEMCODE varchar(5), PKANCODE number(11,0), GEMNM varchar(4), AARDADRPOS number(11,0), X number(31,15), Y number(31,15), SUBADR_TIJ varchar(20), SUBADR_EIN varchar(20), Type varchar(150), Omschrijving varchar(150), CAPAKEY varchar(30), CRABcapa varchar(30), geoCAPAKEY varchar(30)
    -> AttributeRenamer_2
    -> FeatureMerger_2 [SUPPLIER] [off]

Bookmark: Input BevReg_CRAB
001_BevReg_CRAB (reader FFS_2)
    attributes: POSTKODE varchar(4), STRAATKODE varchar(8), NUMMER varchar(5), INDEX varchar(5), GEBDAT varchar(11), GESLACHT varchar(2), NATIONALITEIT number(4,0), VERWERVING number(3,0), REFPERS varchar(2), GEZINSGROOTTE number(3,0), AANTKIND number(3,0), BURGSTAAT varchar(15), NAT_OUD number(4,0), REGISTER varchar(6), sector varchar(5), stadsdeel varchar(16), wijknaam varchar(30), gemeensch varchar(12), BevRegID varchar(10), CRAB_merge varchar(254), CRABadrID varchar(10), GEMNM varchar(4), HUISNR varchar(10), PKANCODE number(11,0), STRAATNM varchar(255), SUBADRES varchar(255)
    -> FeatureMerger [REQUESTOR]
    -> Aggregator_8

Bookmark: Huishoudens
Note: Type huishouden
TestFilter
    DEFAULT_VALUE = <UNFILTERED>
    TEST_LIST = BOOL_OP,OR,COMPOSITE_TEST,<Unused>,TEST_CLAUSE,"TEST @Value(gemeensch) != gemeenschap",particuliere,BOOL_OP,OR,COMPOSITE_TEST,<Unused>,TEST_CLAUSE,"TEST @Value(gemeensch) = gemeenschap",gemeenschap
    particuliere -> PassThrough_Particuliere [off]
    particuliere -> TestFilter_2
    gemeenschap -> PassThrough_Gemeensch [off]
    gemeenschap -> AttributeCreator_7
TestFilter_2
    DEFAULT_VALUE = <UNFILTERED>
    TEST_LIST = BOOL_OP,OR,COMPOSITE_TEST,<Unused>,TEST_CLAUSE,"TEST @Value(REFPERS) = J",@Value(REFPERS) = J
    @Value(REFPERS) = J -> TestFilter_14
Note: Type particulier huishouden
TestFilter_14
    DEFAULT_VALUE = meerpersoonshuishouden
    TEST_LIST = BOOL_OP,OR,COMPOSITE_TEST,<Unused>,TEST_CLAUSE,"TEST @Value(GEZINSGROOTTE) = 01",eenpersoonshuishouden
    eenpersoonshuishouden -> AttributeCreator_9
    meerpersoonshuishouden -> AttributeCreator_10
AttributeCreator_9
    ATTR_TABLE:
      SET_TO ParticHh = 1
      SET_TO EenprsHh = 1
      SET_TO HuishType = Particulier eenpersoonshuishouden
      SET_TO HuishGrootte = @Value(GEZINSGROOTTE)
    -> AttributeKeeper_5
    -> AttributeKeeper_4
AttributeCreator_10
    ATTR_TABLE:
      SET_TO ParticHh = 1
      SET_TO MeerprsHh = 1
      SET_TO HuishType = Particulier meerpersoonshuishouden
      SET_TO HuishGrootte = @Value(GEZINSGROOTTE)
    -> AttributeKeeper_5
    -> AttributeKeeper_4
AttributeKeeper_5
    KEEP_ATTRS = HUISNR,EenprsHh,NATIONALITEIT,GEMNM,HuishGrootte,CRAB_merge,MeerprsHh,GEBDAT,VERWERVING,BURGSTAAT,HuishType,GEZINSGROOTTE,capakey,AANTKIND,ParticHh,_geometry,NAT_OUD,STRAATNM,SUBADRES,BevRegID,REGISTER,PKANCODE,CRABadrID,GESLACHT,REFPERS
    -> Aggregator_4
AttributeCreator_7
    ATTR_TABLE = SET_TO _GEBDAT_YYYYMMDD = @Substring(@Value(GEBDAT),6,4)@Substring(@Value(GEBDAT),3,2)@Substring(@Value(GEBDAT),0,2)
    -> Sorter
Sorter
    SORT_PARM = _GEBDAT_YYYYMMDD ALPHA ASCENDING
    SORTED -> StatisticsCalculator
Note: HuishoudGrootte
StatisticsCalculator
    PREPEND_ATTR_NAME_CHOICE = For multiple results only
    STATS_ATTRS = BevRegID
    COUNT_ATTR = HuishGrootte
    COMPUTE_HISTOGRAM = NO
    GROUP_BY = CRAB_merge CRABadrID
    COMPLETE -> Sampler
Note: Sampl oudste
Sampler
    RATE = 1
    SAMPLE_MODE = No
    SAMPLE_TYPE_LONG = First N Features
    GROUP_BY = CRAB_merge CRABadrID
    SAMPLED -> AttributeCreator_11
AttributeCreator_11
    ATTR_TABLE:
      SET_TO GemeensHh = 1
      SET_TO HuishType = Gemeenschappelijk huishouden
    -> AttributeKeeper_4
    -> AttributeKeeper_6
AttributeKeeper_6
    KEEP_ATTRS = GemeensHh,HUISNR,NATIONALITEIT,GEMNM,HuishGrootte,CRAB_merge,GEBDAT,VERWERVING,BURGSTAAT,HuishType,GEZINSGROOTTE,capakey,AANTKIND,_geometry,NAT_OUD,STRAATNM,SUBADRES,BevRegID,REGISTER,PKANCODE,CRABadrID,GESLACHT,REFPERS
    -> Aggregator_5
Note: Output huishoudens
AttributeKeeper_4
    KEEP_ATTRS = GEZINSGROOTTE,HuishGrootte,sector,HuishType,CRAB_merge,GESLACHT,CRABadrID,NATIONALITEIT,POSTKODE,REGISTER,BURGSTAAT,wijknaam,capakey,NAT_OUD,AANTKIND,INDEX,VERWERVING,STRAATKODE,SUBADRES,BevRegID,HUISNR,GEMNM,PKANCODE,GEBDAT,stadsdeel,STRAATNM,NUMMER,REFPERS
    -> Junction

Bookmark: Gebouweenheden/adres-niveau (adressen-huishoudens)
Note: Inwoners/huishoudens met andere CRAB_merge worden als ander adres beschouwd. >> Nieuwe CRAB_adrID's aangemaakt in FME_BevokingsReg_CRAB >> meer adressen dan in CRAB mogelijk. XY wel afkomstig van CRAB (ontdubbeling van adressen) / Oorzaak: / Adres in rijksregister dat op andere manier aan CRAB gekoppeld wordt (bvb rechtstreeks gekoppeld via adres <> gegeocodeerd = geen rekening met subadres), wordt als ander RRadres beschouwd. / Adres dat na geocoderen niet meer kan gemerged aan CRAB-adres (No clean data: adres BevReg niet in GRAB, wel in CRAB geolocator? Te onderzoeken) >> Nieuwe CRAB_adrID aangemaakt (GL0000)
FeatureMerger_6
    ATTR_CONFLICT_RES = Use Requestor
    MERGE_TYPE = Attributes Only
    GEOM_TYPE = Build Aggregates
    LIST_NAME = _wooneenhList
    ATTR_ACCUM_MODE = Merge Supplier
    PROCESS_DUPS = Yes
    IGNORE_NULLS = No
    JOIN_KEYS = @Value(CRABadrID) @Value(CRABadrID) AUTO
    SUPPLIERS_FIRST = No
    MERGED -> Aggregator_2
    UNREFERENCED -> AttributeCreator_29
Note: Adressen met domicilie
Note: Adressen zonder domicilie
AttributeCreator_29
    ATTR_TABLE:
      SET_TO Domicilie = zonder domicilie
      SET_TO _handhuiscorr_nr = @Substring(@Value(HUISNR),0,@FindRegEx(@Value(HUISNR),[a-zA-Z]))
    -> Aggregator_2
    -> FeatureMerger_7 [REQUESTOR]
Note: Create _adresList
Aggregator_2
    SEP = ,
    AGGREGATE_TYPE = Homogeneous Collection (If Possible)
    ACCUM_ATTRS_NAME = Yes
    LIST_NAME = _adrList
    COUNT_ATTR = _adrCount
    SUM = MeerprsHh ParticHh GemeensHh EenprsHh
    MODE = Geometry - Assemble One Level
    ORDERED = No
    GROUP_BY = capakey
    AGGREGATE -> FeatureMerger_5 [SUPPLIER]

Bookmark: Perceelsniveau
FeatureMerger_5
    ATTR_CONFLICT_RES = Use Requestor
    MERGE_TYPE = Attributes Only
    GEOM_TYPE = Build Aggregates
    ATTR_ACCUM_MODE = Merge Supplier
    PROCESS_DUPS = Yes
    IGNORE_NULLS = No
    JOIN_KEYS = @Value(capakey) @Value(capakey) AUTO
    SUPPLIERS_FIRST = No
    MERGED -> AttributeKeeper_9
    NOT_MERGED -> AttributeKeeper_9
Note: Gebouwtype Andere / MET housingunits
TestFilter_19
    DEFAULT_VALUE = <UNFILTERED>
    TEST_LIST = BOOL_OP,OR,COMPOSITE_TEST,<Unused>,TEST_CLAUSE,"TEST @Value(housingUnitNumber) > 0",@Value(housingUnitNumber) > 0
    @Value(housingUnitNumber) > 0 -> PassThrough_3
    <UNFILTERED> -> TestFilter_22
PassThrough_3: Tester
    TEST_MODE = Automatic
    TEST_DESCRIPTION = ""
    TEST_CLAUSE = TEST 0 = 0
    BOOL_OP = OR
    PASSED -> TestFilter_21 [off]
    PASSED -> VariableRetriever
Note: Nakijken, veel domicilies op 'Andere'
TestFilter_22
    DEFAULT_VALUE = <UNFILTERED>
    TEST_LIST:
      BOOL_OP,OR,COMPOSITE_TEST,<Unused>,TEST_CLAUSE,"TEST @Value(EenprsHh) >= 1
      TEST @Value(MeerprsHh) >= 1
      TEST @Value(GemeensHh) >= 1",Domicilie
    Domicilie -> VariableRetriever
    <UNFILTERED> -> AttributeCreator_8
VariableRetriever
    VARNAME = var_handelspandenExists
    VALUE_ATTR = var_handelspandenExists
    SCOPE = Global
    -> HandelpandenExists
Note: If Handelspanden.shp exists: / Correctie obv handelspanden punten / Else: Correctie obv handelshuis kadaster
HandelpandenExists: Tester
    TEST_MODE = Automatic
    TEST_DESCRIPTION = ""
    TEST_CLAUSE = TEST @Value(var_handelspandenExists) = yes
    BOOL_OP = OR
    PASSED -> SpatialRelator [Requestor]
    FAILED -> TestFilter_23
ListSorter
    ORDER = Ascending
    TYPE = Alphabetic
    SRC_LIST = _adrList{}.HUISNR
    -> ListSorter_2
ListSorter_2
    ORDER = Ascending
    TYPE = Alphabetic
    SRC_LIST = _kadList{}.number
    -> ListFilter
Note: Select eigendommen / met corrhandhuis / uit _kadList{}
ListFilter
    LIST_ATTR = _kadList{}._handhuiscorr
    MODE = DEFAULT
    RESULTLIST_BASE = _kad
    RESULTLIST_SUFFIXLENGTH = 15
    FILTER_VALUES = handhuis
    -> ListFilter_2
Note: Select adressen / zonder domicilie / uit _adrList{}
ListFilter_2
    LIST_ATTR = _adrList{}.Domicilie
    MODE = DEFAULT
    RESULTLIST_BASE = _adr
    RESULTLIST_SUFFIXLENGTH = 15
    FILTER_VALUES = zonder domicilie
    -> AttributeExposer
Note: Geen vergelijking straat. / Kan in principe als twee adressen op zelfde perceel met verschillende straten en zelfde nummer > mogelijk verkeerde adres als correctie handelspand beschouwd / >> verwaarloosbaar
AttributeExposer
    ATTR_LIST = _kad.handhuis{}.number,_adr.zonder_domicili{}.HUISNR,_adr.zonder_domicili{}._handhuiscorr_nr,_kad.handhuis{)._number_nr,_adr.unfiltered{}.HUISNR
    -> ListComparer
Note: Vergelijk number / handhuis selectielijst / met huisnr _adrList{} / zonder domicilie
ListComparer
    FIRST_LIST_ATTR = _adr.zonder_domicili{}.HUISNR
    MODE = DEFAULT
    LIST_NAME_ONLYSECOND = _onlysecond
    SECOND_LIST_ATTR = _kad.handhuis{}.number
    LIST_NAME_ONLYFIRST = _onlyfirst
    LIST_NAME_BOTHSECOND = _bothsecond
    LIST_NAME_BOTHFIRST = _bothfirst
    -> ListElementCounter
ListElementCounter
    LIST_NAME = _bothfirst{}
    CNT_ATTR = _element_count
    -> TestFilter_24
TestFilter_24
    DEFAULT_VALUE = <UNFILTERED>
    TEST_LIST = BOOL_OP,OR,COMPOSITE_TEST,<Unused>,TEST_CLAUSE,"TEST @Value(_element_count) > 0",@Value(_element_count) > 0
    @Value(_element_count) > 0 -> AttributeExposer_2
    <UNFILTERED> -> AttributeRemover_2
AttributeRemover_2
    LIST_ATTRS = _bothfirst{} _bothsecond{} _onlyfirst{} _onlysecond{}
    -> ListComparer_2
Note: Vergelijk number / handhuis selectielijst / met huisnr _adrList{} / met domicilie
ListComparer_2
    FIRST_LIST_ATTR = _adr.unfiltered{}.HUISNR
    MODE = DEFAULT
    LIST_NAME_ONLYSECOND = _onlysecond
    SECOND_LIST_ATTR = _kadList{}.number
    LIST_NAME_ONLYFIRST = _onlyfirst
    LIST_NAME_BOTHSECOND = _bothsecond
    LIST_NAME_BOTHFIRST = _bothfirst
    -> ListElementCounter_2
ListElementCounter_2
    LIST_NAME = _bothfirst{}
    CNT_ATTR = _element_count
    -> TestFilter_25
Note: geen handelspand correctie want / handhuis nummer is bewoond
TestFilter_25
    DEFAULT_VALUE = <UNFILTERED>
    TEST_LIST = BOOL_OP,OR,COMPOSITE_TEST,<Unused>,TEST_CLAUSE,"TEST @Value(_element_count) > 0",@Value(_element_count) > 0
    @Value(_element_count) > 0 -> PassThrough_4
    <UNFILTERED> -> AttributeRemover_3
AttributeRemover_3
    LIST_ATTRS = _bothfirst{} _bothsecond{} _onlyfirst{} _onlysecond{}
    -> ListComparer_3
Note: Vergelijk number / handhuis selectielijst / met huisnr _adrList{} / zonder letters
ListComparer_3
    FIRST_LIST_ATTR = _adr.zonder_domicili{}._handhuiscorr_nr
    MODE = DEFAULT
    LIST_NAME_ONLYSECOND = _onlysecond
    SECOND_LIST_ATTR = _kadList{}._number_nr
    LIST_NAME_ONLYFIRST = _onlyfirst
    LIST_NAME_BOTHSECOND = _bothsecond
    LIST_NAME_BOTHFIRST = _bothfirst
    -> ListElementCounter_3
ListElementCounter_3
    LIST_NAME = _bothfirst{}
    CNT_ATTR = _element_count
    -> TestFilter_27
TestFilter_27
    DEFAULT_VALUE = <UNFILTERED>
    TEST_LIST = BOOL_OP,OR,COMPOSITE_TEST,<Unused>,TEST_CLAUSE,"TEST @Value(_element_count) > 0",@Value(_element_count) > 0
    @Value(_element_count) > 0 -> AttributeExposer_2
    <UNFILTERED> -> ListSearcher_2
AttributeExposer_2
    ATTR_LIST = _bothfirst{}.CRABadrID
    -> AttributeCreator_45
AttributeCreator_45
    ATTR_TABLE = SET_TO _handelspand_corr = 1
    -> AttributeCreator_33
AttributeCreator_33
    ATTR_TABLE = SET_TO _handel.CRABadrID = @Value(_bothfirst{0}.CRABadrID)
    -> AttributeRemover_4
AttributeRemover_4
    LIST_ATTRS = _bothsecond{} _onlyfirst{} _onlysecond{}
    -> PassThrough_5
Note: Laagste adres zonder domicilie
ListSearcher_2
    LIST_ATTR = _adrList{}.Domicilie
    SEARCH_TYPE = First exact match
    PREFIX = _handel.
    INDEX_ATTR = _list_index
    ATTR_VALUE = zonder domicilie
    FOUND -> AttributeCreator_31
    NOT_FOUND -> PassThrough_4
AttributeCreator_31
    ATTR_TABLE:
      SET_TO _bothfirst{0}.CRABadrID = @Value(_handel.CRABadrID)
      SET_TO _handelspand_corr = 1
    -> PassThrough_5
PassThrough_5: Tester
    TEST_MODE = Automatic
    TEST_DESCRIPTION = ""
    TEST_CLAUSE = TEST 0 = 0
    BOOL_OP = OR
    PASSED -> ListAttributeCreator_3
PassThrough_6: Tester
    TEST_MODE = Automatic
    TEST_DESCRIPTION = ""
    TEST_CLAUSE = TEST 0 = 0
    BOOL_OP = OR
    PASSED -> PassThrough_4
PassThrough_4: Tester
    TEST_MODE = Automatic
    TEST_DESCRIPTION = ""
    TEST_CLAUSE = TEST 0 = 0
    BOOL_OP = OR
    PASSED -> AttributeCreator_43
AttributeCreator_8
    ATTR_TABLE = SET_TO Gebouweenh = @Value(_adrCount)
    -> AttributeKeeper_10
    -> AttributeCreator_27
Note: handelpanden: / functie: andere
ListAttributeCreator_3
    MODE = EXPR
    LIST_ATTR_NAME = _bothfirst{}.Functie
    VALUE_EXPR = detailhandel
    -> TestFilter_33
Note: if adrcount > handelspandcorrectie: / - handelspand correctie / else: 1
TestFilter_33
    DEFAULT_VALUE = <UNFILTERED>
    TEST_LIST = BOOL_OP,OR,COMPOSITE_TEST,<Unused>,TEST_CLAUSE,"TEST @Value(_adrCount) = @Value(_handelspand_corr)",@Value(_adrCount) = @Value(_handelspand_corr),BOOL_OP,OR,COMPOSITE_TEST,<Unused>,TEST_CLAUSE,"TEST @Value(_adrCount) > @Value(_handelspand_corr)",@Evaluate(@Value(_adrCount)-@Value(_handelspand_corr))
    @Value(_adrCount) = @Value(_handelspand_corr) -> AttributeCreator_47
    @Evaluate(@Value(_adrCount)-@Value(_handelspand_corr)) -> AttributeCreator_46
Note: minimum 1 wooneenh / wooneenh = 1
AttributeCreator_47
    ATTR_TABLE:
      SET_TO Wooneenh = 1
      SET_TO _wooneenh_index = @Evaluate(@Value(_handelspand_corr)-1)
    -> ListAttributeCreator_2
Note: laatste handelspand: / toch funcitie woning
ListAttributeCreator_2
    MODE = EXPR
    LIST_ATTR_NAME = _bothfirst{@Value(_wooneenh_index)}.Functie
    VALUE_EXPR = woning
    -> Junction_3
Note: wooneenh = adrCount - handelspand corr
AttributeCreator_46
    ATTR_TABLE = SET_TO Wooneenh = @Evaluate(@Value(_adrCount)-@Value(_handelspand_corr))
    -> Junction_3
Junction_3
    -> AttributeRenamer_3
Note: adrcount
AttributeCreator_43
    ATTR_TABLE = SET_TO Wooneenh = @Evaluate(@Value(_adrCount))
    -> AttributeRenamer_3
AttributeRenamer_3
    ATTR_TABLE = RENAME_SET_DEFAULT _adrCount > Gebouweenh
    -> PassThrough_7
PassThrough_7: Tester
    TEST_MODE = Automatic
    TEST_DESCRIPTION = ""
    TEST_CLAUSE = TEST 0 = 0
    BOOL_OP = OR
    PASSED -> AttributeCreator_34
    PASSED -> AttributeKeeper_10
Note: Perceelsinfo aantal / wooneenheden, huishoudens, gebouwtype
AttributeKeeper_10
    KEEP_ATTRS = housingUnitNumber,constructionType,capakey,descriptPrivate,MeerprsHh,GebouwType,Gebouweenh,GemeensHh,Wooneenh,constructionIndication,nature,EenprsHh,ParticHh
    KEEP_LIST = _kadList{}.GebouwType _kadList{}.aard _kadList{}.bathroomNumber _kadList{}.bisNumber _kadList{}.block _kadList{}.bouwjaar _kadList{}.builtSurface _kadList{}.cadastralIncome _kadList{}.cadastralIncomePerSurface _kadList{}.cadastralIncomePerSurfaceOtherDi _kadList{}.capakey _kadList{}.centralHeating _kadList{}.charCadastralIncome _kadList{}.constructionIndication _kadList{}.constructionQuality _kadList{}.constructionType _kadList{}.constructionYear _kadList{}.crossDetail _kadList{}.dateEndExoneration _kadList{}.dateSituation _kadList{}.decrete _kadList{}.descriptPrivate _kadList{}.divCad _kadList{}.exponentLetter _kadList{}.exponentNumber _kadList{}.floor _kadList{}.floorNumberAboveground _kadList{}.floorSituation _kadList{}.garageNumber _kadList{}.garret _kadList{}.housingUnitNumber _kadList{}.matUtil _kadList{}.nature _kadList{}.nisCom _kadList{}.notTaxedMatUtil _kadList{}.number _kadList{}.numberCadastralIncome _kadList{}.order _kadList{}.partNumber _kadList{}.physModYear _kadList{}.placeNumber _kadList{}.polWa _kadList{}.primaryNumber _kadList{}.propertySituationIdf _kadList{}.section _kadList{}.soilIndex _kadList{}.soilRent _kadList{}.street_code _kadList{}.street_situation _kadList{}.street_translation _kadList{}.surfaceNotTaxable _kadList{}.surfaceTaxable _kadList{}.surfaceVerif _kadList{}.usedSurface
    -> ListRenamer_2
Note: adres/gebouwenhLijst nog niet wegschrijven / correctie handelshuis nog niet gebeurd / Hierna mergen
ListRenamer_2
    LIST_ACTION = Rename
    LIST_COMPONENT_NAMES = _kadList{},_kadparcelList{}
    LIST_NAME = _kadList{}
    LEAVE_ORIG = No
    -> FeatureMerger_9 [REQUESTOR]
Note: Merge gebouweenheden info to PERC / unreferenced: capakey missing (OD)
FeatureMerger_9
    ATTR_CONFLICT_RES = Use Requestor
    MERGE_TYPE = Attributes Only
    ATTR_ACCUM_MODE = Merge Supplier
    PROCESS_DUPS = No
    IGNORE_NULLS = No
    JOIN_KEYS = @Value(capakey) @Value(capakey) AUTO
    SUPPLIERS_FIRST = No
    MERGED -> 003_KADparcel_Gebouweenheden (writer FFS_6)
    NOT_MERGED -> 003_KADparcel_Gebouweenheden (writer FFS_6)

Bookmark: LGGR_GebouwType Perceelsniveau
AttributeKeeper_9
    KEEP_ATTRS = MeerprsHh,constructionType,ParticHh,constructionIndication,Domicilie,GemeensHh,housingUnitNumber,EenprsHh,_adrCount,capakey,geoCAPAKEY,descriptPrivate,nature
    KEEP_LIST = _adrList{}.CRABadrID _adrList{}.Domicilie _adrList{}.HUISNR _adrList{}._handhuiscorr_nr _kadList{}.GebouwType _kadList{}._handhuiscorr _kadList{}._number_nr _kadList{}.aard _kadList{}.bathroomNumber _kadList{}.bisNumber _kadList{}.block _kadList{}.bouwjaar _kadList{}.builtSurface _kadList{}.cadastralIncome _kadList{}.cadastralIncomePerSurface _kadList{}.cadastralIncomePerSurfaceOtherDi _kadList{}.capakey _kadList{}.centralHeating _kadList{}.charCadastralIncome _kadList{}.constructionIndication _kadList{}.constructionQuality _kadList{}.constructionType _kadList{}.constructionYear _kadList{}.crossDetail _kadList{}.dateEndExoneration _kadList{}.dateSituation _kadList{}.decrete _kadList{}.descriptPrivate _kadList{}.divCad _kadList{}.exponentLetter _kadList{}.exponentNumber _kadList{}.floor _kadList{}.floorNumberAboveground _kadList{}.floorSituation _kadList{}.garageNumber _kadList{}.garret _kadList{}.housingUnitNumber _kadList{}.matUtil _kadList{}.nature _kadList{}.nisCom _kadList{}.notTaxedMatUtil _kadList{}.number _kadList{}.numberCadastralIncome _kadList{}.order _kadList{}.partNumber _kadList{}.physModYear _kadList{}.placeNumber _kadList{}.polWa _kadList{}.primaryNumber _kadList{}.propertySituationIdf _kadList{}.section _kadList{}.soilIndex _kadList{}.soilRent _kadList{}.street_code _kadList{}.street_situation _kadList{}.street_translation _kadList{}.surfaceNotTaxable _kadList{}.surfaceTaxable _kadList{}.surfaceVerif _kadList{}.usedSurface
    -> AttributeCreator_26
AttributeCreator_26
    ATTR_TABLE = SET_TO constructionIndication = FME_CONDITIONAL:DEFAULT_VALUE'@PadLeft(@Value(constructionIndication),3,0)'BOOL_OP;OR;COMPOSITE_TEST;<Unused>;TEST constructionIndication ATTRIBUTE_VALUE_NULL _FME_BLANK_STRING_;TEST constructionIndication ATTRIBUTE_IS_EMPTY _FME_BLANK_STRING_;TEST constructionIndication ATTRIBUTE_IS_MISSING _FME_BLANK_STRING_'_FME_NO_OP_'FME_NUM_CONDITIONS2___
    -> TestFilter_20
Note: Select verblijfseigendommen
TestFilter_20
    DEFAULT_VALUE = Andere
    TEST_LIST:
      BOOL_OP,COMPOSITE,COMPOSITE_TEST,"""(1 OR 2 OR 3 OR 4 OR 5 OR 6 OR 7 OR 8 OR 9 OR 10 OR 11) AND 12""",TEST_CLAUSE,"TEST @Value(constructionIndication) LIKE %010%
      TEST @Value(constructionIndication) LIKE %030%
      TEST @Value(constructionIndication) LIKE %031%
      TEST @Value(constructionIndication) LIKE %032%
      TEST @Value(constructionIndication) LIKE %033%
      TEST @Value(constructionIndication) LIKE %040%
      TEST @Value(constructionIndication) LIKE %041%
      TEST @Value(constructionIndication) LIKE %050%
      TEST @Value(constructionIndication) LIKE %060%
      TEST @Value(constructionIndication) LIKE %070%
      TEST @Value(constructionIndication) LIKE %080%
      TEST @Value(constructionType) LIKE %A%",Huis in gesloten bebouwing,BOOL_OP,COMPOSITE,COMPOSITE_TEST,"""(1 OR 2 OR 3 OR 4 OR 5 OR 6 OR 7 OR 8 OR 9 OR 10 OR 11) AND 12""",TEST_CLAUSE,"TEST @Value(constructionIndication) LIKE %010%
      TEST @Value(constructionIndication) LIKE %030%
      TEST @Value(constructionIndication) LIKE %031%
      TEST @Value(constructionIndication) LIKE %032%
      TEST @Value(constructionIndication) LIKE %033%
      TEST @Value(constructionIndication) LIKE %040%
      TEST @Value(constructionIndication) LIKE %041%
      TEST @Value(constructionIndication) LIKE %050%
      TEST @Value(constructionIndication) LIKE %060%
      TEST @Value(constructionIndication) LIKE %070%
      TEST @Value(constructionIndication) LIKE %080%
      TEST @Value(constructionType) LIKE %B%",Huis in half open bebouwing,BOOL_OP,COMPOSITE,COMPOSITE_TEST,"""(1 OR 2 OR 3 OR 4 OR 5 OR 6 OR 7 OR 8 OR 9 OR 10 OR 11 OR 12 OR 13) AND 14""",TEST_CLAUSE,"TEST @Value(constructionIndication) LIKE %010%
      TEST @Value(constructionIndication) LIKE %030%
      TEST @Value(constructionIndication) LIKE %031%
      TEST @Value(constructionIndication) LIKE %032%
      TEST @Value(constructionIndication) LIKE %033%
      TEST @Value(constructionIndication) LIKE %040%
      TEST @Value(constructionIndication) LIKE %041%
      TEST @Value(constructionIndication) LIKE %050%
      TEST @Value(constructionIndication) LIKE %060%
      TEST @Value(constructionIndication) LIKE %070%
      TEST @Value(constructionIndication) LIKE %080%
      TEST @Value(constructionIndication) LIKE %020%
      TEST @Value(constructionIndication) LIKE %470%
      TEST @Value(constructionType) LIKE %C%",Huis in open bebouwing, hoeve of kasteel,BOOL_OP,OR,COMPOSITE_TEST,<Unused>,TEST_CLAUSE,"TEST @Value(constructionIndication) LIKE %100%
      TEST @Value(constructionIndication) LIKE %101%
      TEST @Value(constructionIndication) LIKE %104%
      TEST @Value(constructionIndication) LIKE %105%
      TEST @Value(constructionIndication) LIKE %110%
      TEST @Value(constructionIndication) LIKE %111%
      TEST @Value(constructionIndication) LIKE %114%
      TEST @Value(constructionIndication) LIKE %115%
      TEST @Value(constructionIndication) LIKE %999%",Buildings en flatgebouwen met appartementen,BOOL_OP,OR,COMPOSITE_TEST,<Unused>,TEST_CLAUSE,"TEST @Value(constructionIndication) LIKE %200%
      TEST @Value(constructionIndication) LIKE %210%
      TEST @Value(constructionIndication) LIKE %220%
      TEST @Value(constructionIndication) LIKE %230%",Handelshuis
    Huis in gesloten bebouwing -> AttributeCreator_19
    Huis in half open bebouwing -> AttributeCreator_21
    Huis in open bebouwing, hoeve of kasteel -> AttributeCreator_22
    Buildings en flatgebouwen met appartementen -> AttributeCreator_23
    Handelshuis -> AttributeCreator_24
    Andere -> AttributeCreator_25
AttributeCreator_19
    ATTR_LIST = GebouwType,Huizen in gesloten bebouwing
    -> PassThrough_3
AttributeCreator_21
    ATTR_LIST = GebouwType,Huizen in half open bebouwing
    -> PassThrough_3
AttributeCreator_22
    ATTR_LIST = GebouwType,Huizen in open bebouwing, hoeven en kastelen
    -> PassThrough_3
AttributeCreator_23
    ATTR_LIST = GebouwType,Buildings en flatgebouwen met appartementen
    -> PassThrough_3
AttributeCreator_24
    ATTR_LIST = GebouwType,Handelshuizen
    -> PassThrough_3
AttributeCreator_25
    ATTR_LIST = GebouwType,Andere
    -> TestFilter_19

Bookmark: Uitzonderingen meerdere REFPERS per adres
TestFilter_21
    DEFAULT_VALUE = <UNFILTERED>
    TEST_LIST:
      BOOL_OP,AND,COMPOSITE_TEST,<Unused>,TEST_CLAUSE,"TEST @Value(_adrCount) = 0
      TEST @Value(housingUnitNumber) = 0",_adrCount AND housingUnitNumber = 0,BOOL_OP,AND,COMPOSITE_TEST,<Unused>,TEST_CLAUSE,"TEST @Value(housingUnitNumber) = 0",housingUnitNumber = 0,BOOL_OP,AND,COMPOSITE_TEST,<Unused>,TEST_CLAUSE,"TEST @Value(_adrCount) = 0",_adrCount = 0,BOOL_OP,AND,COMPOSITE_TEST,<Unused>,TEST_CLAUSE,"TEST @Value(housingUnitNumber) > @Value(_adrCount)",housingUnitNumber > _adrCount,BOOL_OP,AND,COMPOSITE_TEST,<Unused>,TEST_CLAUSE,"TEST @Value(housingUnitNumber) < @Value(_adrCount)",housingUnitNumber < _adrCount,BOOL_OP,AND,COMPOSITE_TEST,<Unused>,TEST_CLAUSE,"TEST @Value(housingUnitNumber) = @Value(_adrCount)",housingUnitNumber = _adrCount
    _adrCount AND housingUnitNumber = 0 -> TestFilter_21__adrCount_AND_housingUnitNumber___0
    housingUnitNumber = 0 -> TestFilter_21_housingUnitNumber___0
    _adrCount = 0 -> TestFilter_21__adrCount___0
    housingUnitNumber > _adrCount -> TestFilter_21_housingUnitNumber____adrCount
    housingUnitNumber < _adrCount -> TestFilter_21_housingUnitNumber____adrCount_2
    housingUnitNumber = _adrCount -> TestFilter_21_housingUnitNumber____adrCount_3
    <UNFILTERED> -> TestFilter_21__Unfiltered_
TestFilter_21__adrCount_AND_housingUnitNumber___0: Inspector
Note: correctie fout gematchedte CRAB en percelen cfr voorbeelden. / Correctiealgoritme mogelijk maar niet relevant voor dergelijk klein percentage. / >> _adrCount CRAB = aantal wooneenhedne / - correctie handelshuis
TestFilter_21_housingUnitNumber___0: Inspector
TestFilter_21__adrCount___0: Inspector
TestFilter_21_housingUnitNumber____adrCount: Inspector
TestFilter_21_housingUnitNumber____adrCount_2: Inspector
TestFilter_21_housingUnitNumber____adrCount_3: Inspector
TestFilter_21__Unfiltered_: Inspector

Bookmark: Select handelshuis correctie
Note: correctie handelshuis / als indicie handelshuis of aard handelshuis of descriptPrivate HAND/HUIS / EN adrCount > housing units kadaster EN 1 zonder domicilie >> zelfde nummer als KAD of laagste zonder domicilie
TestFilter_23
    DEFAULT_VALUE = <UNFILTERED>
    TEST_LIST:
      BOOL_OP,COMPOSITE,COMPOSITE_TEST,"""1 AND (2 OR 3 OR 4)""",TEST_CLAUSE,"TEST @Value(_adrCount) > @Value(housingUnitNumber)
      TEST @Value(GebouwType) = Handelshuizen
      TEST @Value(nature) LIKE %407%
      TEST @Value(descriptPrivate) LIKE %HAND/HUIS%",-1 Handelshuis
    -1 Handelshuis -> ListSearcher
    <UNFILTERED> -> PassThrough_6
ListSearcher
    LIST_ATTR = _adrList{}.Domicilie
    SEARCH_TYPE = First exact match
    INDEX_ATTR = _list_index
    ATTR_VALUE = zonder domicilie
    FOUND -> ListSorter
    NOT_FOUND -> PassThrough_6

Bookmark: OUTPUT: huishoudens + info refpersoon of oudste
003_Huishoudens (writer FFS_4)
    attributes: POSTKODE varchar(4), STRAATKODE varchar(8), NUMMER varchar(5), INDEX varchar(5), GEBDAT varchar(11), GESLACHT varchar(2), NATIONALITEIT number(4,0), VERWERVING number(3,0), REFPERS varchar(2), GEZINSGROOTTE number(3,0), AANTKIND number(3,0), BURGSTAAT varchar(15), NAT_OUD number(4,0), REGISTER varchar(6), sector varchar(5), stadsdeel varchar(16), wijknaam varchar(30), BevRegID varchar(10), CRAB_merge varchar(254), CRABadrID varchar(10), GEMNM varchar(4), STRAATNM varchar(255), HUISNR varchar(10), PKANCODE number(11,0), SUBADRES varchar(255), capakey varchar(30), HuishGrootte number(10,0), HuishType varchar(60)
003_Huishoudens (writer ESRISHAPE_1)
    attributes: POSTKODE char(4), STRAATKODE char(8), NUMMER char(5), INDEX char(5), GEBDAT char(11), GESLACHT char(2), NATIONALIT number(4,0), VERWERVING number(3,0), REFPERS char(2), GEZINSGROO number(3,0), AANTKIND number(3,0), BURGSTAAT char(15), NAT_OUD number(4,0), REGISTER char(6), sector char(5), stadsdeel char(16), wijknaam char(30), BevRegID char(10), CRAB_merge char(254), CRABadrID char(10), GEMNM char(4), STRAATNM char(254), HUISNR char(10), PKANCODE number(11,0), SUBADRES char(254), capakey char(30), HuishGroot number(10,0), HuishType char(60)

Bookmark: Uitzonderingen meerdere REFPERS per adres
TestFilter_3
    DEFAULT_VALUE = <UNFILTERED>
    TEST_LIST = BOOL_OP,OR,COMPOSITE_TEST,<Unused>,TEST_CLAUSE,"TEST @Value(REFPERS) = J",@Value(REFPERS) = J
    @Value(REFPERS) = J -> DuplicateFilter
DuplicateFilter
    INPUT_ORDERED_CHOICE = No
    KEYATTR = CRAB_merge HUISNR SUBADRES STRAATNM CRABadrID
    UNIQUE -> DuplicateFilter_Unique
    DUPLICATE -> DuplicateFilter_Duplicate
DuplicateFilter_Unique: Inspector
DuplicateFilter_Duplicate: Inspector

Bookmark: Uitzonderingen testen foutieve data gemeensch
Note: Test gemeensch die REFPERS J
TestFilter_12
    DEFAULT_VALUE = <UNFILTERED>
    TEST_LIST = BOOL_OP,OR,COMPOSITE_TEST,<Unused>,TEST_CLAUSE,"TEST @Value(REFPERS) = N",@Value(REFPERS) = N
    @Value(REFPERS) = N -> OK_TestFilter_12__Value_REFPERS____N
    <UNFILTERED> -> NIETOK_TestFilter_12__Unfiltered_
OK_TestFilter_12__Value_REFPERS____N: Inspector
NIETOK_TestFilter_12__Unfiltered_: Inspector
Note: Test gemeensch die > 01 gezinsgrootte
TestFilter_13
    DEFAULT_VALUE = <UNFILTERED>
    TEST_LIST = BOOL_OP,OR,COMPOSITE_TEST,<Unused>,TEST_CLAUSE,"TEST @Value(GEZINSGROOTTE) > 1",GEZINSGROOTTE>1
    GEZINSGROOTTE>1 -> NIETOK_TestFilter_13_GEZINSGROOTTE_1
    <UNFILTERED> -> OK_TestFilter_13__Unfiltered_
NIETOK_TestFilter_13_GEZINSGROOTTE_1: Inspector
OK_TestFilter_13__Unfiltered_: Inspector
Note: Test Gemeensch huishouden + andere op zelfde adres?
FeatureMerger_3
    MERGE_TYPE = Attributes Only
    ATTR_ACCUM_MODE = Prefix Supplier
    PROCESS_DUPS = No
    IGNORE_NULLS = No
    JOIN_KEYS = @Value(CRAB_merge) @Value(CRAB_merge) AUTO @Value(CRABadrID) @Value(CRABadrID) AUTO
    SUPPLIERS_FIRST = No
    SUPPLIER_PREFIX = part_
    MERGED -> NIETOK_FeatureMerger_3_Merged
    NOT_MERGED -> OK_FeatureMerger_3_NotMerged
    REFERENCED -> FeatureMerger_3_Referenced
    UNREFERENCED -> FeatureMerger_3_Unreferenced
    DUPLICATE_SUPPLIER -> FeatureMerger_3_DuplicateSupplier
NIETOK_FeatureMerger_3_Merged: Inspector
OK_FeatureMerger_3_NotMerged: Inspector
FeatureMerger_3_Referenced: Inspector
FeatureMerger_3_Unreferenced: Inspector
FeatureMerger_3_DuplicateSupplier: Inspector

Bookmark: Check if Handelspand shapefile exists
Creator
    GEOMTYPE = Geometry Object
    NUM = 1
    CREATED -> ParameterFetcher_2
ParameterFetcher_2
    ATTR_LIST = _filePath {$(SourceDataset_Handelspanden)}
    -> PythonCaller
Note: Check if Handelspanden.shp exists
PythonCaller
    PYTHONSYMBOL = processFeature
    PYTHONSOURCE:
      import os
      import fme
      import fmeobjects
      # Template Function interface:
      def processFeature(feature):
          file_path=feature.getAttribute("_filePath")
          doesFileExist = os.path.exists(file_path)
          feature.setAttribute("_fileExists", doesFileExist)
    NEW_ATTRIBUTES = _fileExists
    -> FileExists
FileExists: TestFilter
    DEFAULT_VALUE = no
    TEST_LIST = BOOL_OP,OR,COMPOSITE_TEST,<Unused>,TEST_CLAUSE,"TEST @Value(_fileExists) = Yes",yes
    yes -> VariableSetter
    no -> VariableSetter_2
VariableSetter
    VALUE = yes
    VARNAME = var_handelspandenExists
    SCOPE = Global
    -> FeatureReader [INITIATOR]
VariableSetter_2
    VALUE = no
    VARNAME = var_handelspandenExists
    SCOPE = Global
    -> VariableSetter_2_Output
VariableSetter_2_Output: Inspector

Bookmark: Correctie handelspanden
FeatureReader
    OUTPUT_FEATURES_DISPLAY = Based on Connections
    SHAPE_CLIP_TO_ENVELOPE = NO
    ATTR_ACCUM_MODE = Only Use Result
    SHAPE_USE_SEARCH_ENVELOPE = NO
    SHAPE_ENCODING = SYSTEM
    SHAPE_UPPER_CASE_ATTR_NAMES = No
    INTERACT = <No Spatial Filter>
    SHAPE_SIMPLE_DONUT_GEOMETRY = simple
    DATASET = ..\data\input\Handelspanden.shp
    COMBINE_GEOM = Use Result
    FEATURETYPES_RADIO = FEATURETYPES
    FORMAT = SHAPE
    <OTHER> -> AttributeExposer_3
AttributeExposer_3
    ATTR_LIST = HUISNRTOEV,HUISNR,STRAAT,POSTCODE
    -> Counter
Counter
    START = 1
    SCOPE = Global
    CNT_ATTR = HandelID
    DOMAIN = counter
    -> TestFilter_28
    -> 003_Handelspanden (writer ESRISHAPE_1)
TestFilter_28
    DEFAULT_VALUE = <UNFILTERED>
    TEST_LIST = BOOL_OP,OR,COMPOSITE_TEST,<Unused>,TEST_CLAUSE,"TEST @Value(HUISNRTOEV) CONTAINS_REGEX -", - ..,BOOL_OP,OR,COMPOSITE_TEST,<Unused>,TEST_CLAUSE,"TEST @Value(HUISNRTOEV) CONTAINS_REGEX ^[A-Z]$",Letter,BOOL_OP,OR,COMPOSITE_TEST,<Unused>,TEST_CLAUSE,"TEST @Value(HUISNRTOEV) TYPE INT",Integer
    - .. -> AttributeCreator_38
    - .. -> AttributeCreator_42
    Letter -> AttributeCreator_39
    Integer -> AttributeCreator_40
    <UNFILTERED> -> AttributeCreator_41
AttributeCreator_38
    ATTR_TABLE:
      SET_TO _huisnr = @Substring(@Value(HUISNRTOEV),@FindRegEx(@Value(HUISNRTOEV),[0-9]), -1)
      SET_TO _huisnr_nr = @Substring(@Value(_huisnr),0,@FindRegEx(@Value(_huisnr),[a-zA-Z]))
    -> PassThrough_8
AttributeCreator_42
    ATTR_TABLE:
      SET_TO _huisnr = @Substring(@Value(HUISNR),0,-1)
      SET_TO _huisnr_nr = @Substring(@Value(_huisnr),0,@FindRegEx(@Value(_huisnr),[a-zA-Z]))
    -> PassThrough_8
AttributeCreator_39
    ATTR_TABLE:
      SET_TO _huisnr = @Value(HUISNR)@Value(HUISNRTOEV)
      SET_TO _huisnr_nr = @Substring(@Value(_huisnr),0,@FindRegEx(@Value(_huisnr),[a-zA-Z]))
    -> PassThrough_8
AttributeCreator_40
    ATTR_TABLE:
      SET_TO _subadr = @PadLeft(@Value(HUISNRTOEV),4,0)
      SET_TO _huisnr = @Substring(@Value(HUISNR),0,-1)
      SET_TO _huisnr_nr = @Substring(@Value(_huisnr),0,@FindRegEx(@Value(_huisnr),[a-zA-Z]))
    -> PassThrough_8
AttributeCreator_41
    ATTR_TABLE:
      SET_TO _huisnr = @Substring(@Value(HUISNR),0,-1)
      SET_TO _huisnr_nr = @Substring(@Value(_huisnr),0,@FindRegEx(@Value(_huisnr),[a-zA-Z]))
    -> PassThrough_8
PassThrough_8: Tester
    TEST_MODE = Automatic
    TEST_DESCRIPTION = ""
    TEST_CLAUSE = TEST 0 = 0
    BOOL_OP = OR
    PASSED -> SpatialRelator [Supplier]
SpatialRelator
    AGGREGATE_HANDLING = Yes
    CALC_CARD = No
    LIST_NAME = _handelsList
    ATTR_PREFIX = _hand.
    ATTR_ACCUM_MODE = Prefix Supplier
    CURVE_BOUNDARY_RULE_PARAM = Default Rule
    PREDICATES = INTERSECTS
    SUCCESS_ATTR = _handelscount
    -> TestFilter_34
TestFilter_34
    DEFAULT_VALUE = <UNFILTERED>
    TEST_LIST = BOOL_OP,OR,COMPOSITE_TEST,<Unused>,TEST_CLAUSE,"TEST @Value(_handelscount) > 0",handhuis
    handhuis -> ListSorter_3
    <UNFILTERED> -> PassThrough_11
ListSorter_3
    ORDER = Ascending
    TYPE = Alphabetic
    SRC_LIST = _adrList{}.HUISNR
    -> ListSorter_4
ListSorter_4
    ORDER = Ascending
    TYPE = Alphabetic
    SRC_LIST = _kadList{}.number
    -> ListFilter_3
Note: Select adressen / zonder domicilie / uit _adrList{}
ListFilter_3
    LIST_ATTR = _adrList{}.Domicilie
    MODE = DEFAULT
    RESULTLIST_BASE = _adr
    RESULTLIST_SUFFIXLENGTH = 15
    FILTER_VALUES = zonder domicilie
    -> AttributeExposer_4
AttributeExposer_4
    ATTR_LIST = _adr.zonder_domicili{}.HUISNR,_adr.zonder_domicili{}._handhuiscorr_nr,_adr.unfiltered{}.HUISNR
    -> ListComparer_4
Note: Vergelijk number / handpand lijst / met huisnr _adrList{} / zonder domicilie
ListComparer_4
    FIRST_LIST_ATTR = _adr.zonder_domicili{}.HUISNR
    MODE = DEFAULT
    LIST_NAME_ONLYSECOND = _onlysecond
    SECOND_LIST_ATTR = _handelsList{}._huisnr
    LIST_NAME_ONLYFIRST = _onlyfirst
    LIST_NAME_BOTHSECOND = _bothsecond
    LIST_NAME_BOTHFIRST = _bothfirst
    -> ListElementCounter_4
ListElementCounter_4
    LIST_NAME = _bothfirst{}
    CNT_ATTR = _handelspand_corr
    -> TestFilter_30
TestFilter_30
    DEFAULT_VALUE = <UNFILTERED>
    TEST_LIST = BOOL_OP,OR,COMPOSITE_TEST,<Unused>,TEST_CLAUSE,"TEST @Value(_handelspand_corr) > 0",@Value(_handelspand_corr) > 0
    @Value(_handelspand_corr) > 0 -> AttributeExposer_5
    <UNFILTERED> -> AttributeRemover_5
AttributeRemover_5
    LIST_ATTRS = _bothfirst{} _bothsecond{} _onlyfirst{} _onlysecond{}
    -> ListComparer_5
Note: Vergelijk number / handhuis selectielijst / met huisnr _adrList{} / met domicilie
ListComparer_5
    FIRST_LIST_ATTR = _adr.unfiltered{}.HUISNR
    MODE = DEFAULT
    LIST_NAME_ONLYSECOND = _onlysecond
    SECOND_LIST_ATTR = _handelsList{}._huisnr
    LIST_NAME_ONLYFIRST = _onlyfirst
    LIST_NAME_BOTHSECOND = _bothsecond
    LIST_NAME_BOTHFIRST = _bothfirst
    -> ListElementCounter_5
ListElementCounter_5
    LIST_NAME = _bothfirst{}
    CNT_ATTR = _handelspand_corr
    -> TestFilter_31
Note: geen handelspand correctie want / handhuis nummer is bewoond
TestFilter_31
    DEFAULT_VALUE = <UNFILTERED>
    TEST_LIST = BOOL_OP,OR,COMPOSITE_TEST,<Unused>,TEST_CLAUSE,"TEST @Value(_handelspand_corr) > 0",@Value(_handelspand_corr) > 0
    @Value(_handelspand_corr) > 0 -> PassThrough_9
    <UNFILTERED> -> AttributeRemover_6
AttributeRemover_6
    LIST_ATTRS = _bothfirst{} _bothsecond{} _onlyfirst{} _onlysecond{}
    -> ListComparer_6
Note: Vergelijk number / handhuis selectielijst / met huisnr _adrList{} / zonder letters
ListComparer_6
    FIRST_LIST_ATTR = _adr.zonder_domicili{}._handhuiscorr_nr
    MODE = DEFAULT
    LIST_NAME_ONLYSECOND = _onlysecond
    SECOND_LIST_ATTR = _handelsList{}._huisnr_nr
    LIST_NAME_ONLYFIRST = _onlyfirst
    LIST_NAME_BOTHSECOND = _bothsecond
    LIST_NAME_BOTHFIRST = _bothfirst
    -> ListElementCounter_6
ListElementCounter_6
    LIST_NAME = _bothfirst{}
    CNT_ATTR = _handelspand_corr
    -> TestFilter_32
Note: Door slechte notatie adressen in handelslist? / beter geen correctie? afhankelijk v kwaliteit handelszaken dataset
TestFilter_32
    DEFAULT_VALUE = <UNFILTERED>
    TEST_LIST = BOOL_OP,OR,COMPOSITE_TEST,<Unused>,TEST_CLAUSE,"TEST @Value(_handelspand_corr) > 0",@Value(_handelspand_corr) > 0
    @Value(_handelspand_corr) > 0 -> AttributeExposer_5
    <UNFILTERED> -> ListSearcher_3
AttributeExposer_5
    ATTR_LIST = _bothfirst{}.CRABadrID,_bothsecond{}.HandelID
    -> ListConcatenator
ListConcatenator
    LIST_ATTR = _bothfirst{}.CRABadrID
    SEP = ,
    VAL_ATTR = _handel.CRABadrID
    DROP_EMPTY_PARTS = Yes
    -> AttributeRemover_7
AttributeRemover_7
    LIST_ATTRS = _onlyfirst{} _onlysecond{}
    -> PassThrough_10
Note: Laagste adres zonder domicilie
ListSearcher_3
    LIST_ATTR = _adrList{}.Domicilie
    SEARCH_TYPE = First exact match
    PREFIX = _handel.
    INDEX_ATTR = _list_index
    ATTR_VALUE = zonder domicilie
    FOUND -> AttributeCreator_30
    NOT_FOUND -> PassThrough_9
Note: Geen handelID
AttributeCreator_30
    ATTR_TABLE:
      SET_TO _bothfirst{0}.CRABadrID = @Value(_handel.CRABadrID)
      SET_TO _handelspand_corr = 1
    -> PassThrough_10
PassThrough_11: Tester
    TEST_MODE = Automatic
    TEST_DESCRIPTION = ""
    TEST_CLAUSE = TEST 0 = 0
    BOOL_OP = OR
    PASSED -> PassThrough_9
PassThrough_9: Tester
    TEST_MODE = Automatic
    TEST_DESCRIPTION = ""
    TEST_CLAUSE = TEST 0 = 0
    BOOL_OP = OR
    PASSED -> Junction_2

Bookmark: OUTPUT: handelspanden
003_Handelspanden (writer ESRISHAPE_1)
    attributes: NAAM char(50), STRAAT char(50), HUISNR char(5), HUISNRTOEV char(5), POSTCODE char(4), DEELGEM char(40), BRANCHE char(50), PRODGROEP char(50), HandelID char(10)

Bookmark: Set functie en handelID
VariableRetriever_2
    VARNAME = var_handelspandenExists
    VALUE_ATTR = var_handelspandenExists
    SCOPE = Global
    -> HandelpandenExists_2
HandelpandenExists_2: Tester
    TEST_MODE = Automatic
    TEST_DESCRIPTION = ""
    TEST_CLAUSE = TEST @Value(var_handelspandenExists) = yes
    BOOL_OP = OR
    PASSED -> ListSearcher_4
    FAILED -> ListSearcher_5
Note: ListSearcher_4
ListSearcher_4
    LIST_ATTR = _bothfirst{}.CRABadrID
    SEARCH_TYPE = First exact match
    INDEX_ATTR = _list_index
    ATTR_VALUE = @Value(CRABadrID)
    FOUND -> ListIndexer
Note: functie
ListIndexer
    LIST_ATTR = _bothfirst{}
    INDEX = @Value(_list_index)
    -> ListIndexer_2
Note: HandelID
ListIndexer_2
    LIST_ATTR = _bothsecond{}
    INDEX = @Value(_list_index)
    -> AttributeRemover_8
AttributeRemover_8
    REMOVE_ATTRS = _list_index,var_handelspandenExists
    LIST_ATTRS = _bothfirst{} _bothfirst{}.CRABadrID _bothsecond{} _bothsecond{}.HandelID
    -> AttributeCreator_6
ListSearcher_5
    LIST_ATTR = _bothfirst{}.CRABadrID
    SEARCH_TYPE = First exact match
    INDEX_ATTR = _list_index
    ATTR_VALUE = @Value(CRABadrID)
    FOUND -> ListIndexer_3
Note: functie
ListIndexer_3
    LIST_ATTR = _bothfirst{}
    INDEX = @Value(_list_index)
    -> AttributeCreator_6

Bookmark: OUTPUT: KADparcel_gebouweenheden
  _kadparcelList{}
  _gebouweenh{}
003_KADparcel_Gebouweenheden (writer FFS_6)
    attributes: Gebouweenh number(3,0), Wooneenh number(3,0), constructionIndication varchar(254), capakey varchar(17), nature varchar(254), descriptPrivate varchar(254), constructionType varchar(254), housingUnitNumber number(3,0), _kadparcelList{}.constructionIndication number(4,0), _kadparcelList{}.propertySituationIdf number(8,0), _kadparcelList{}.divCad number(5,0), _kadparcelList{}.section varchar(1), _kadparcelList{}.primaryNumber number(3,0), _kadparcelList{}.bisNumber number(2,0), _kadparcelList{}.exponentLetter varchar(1), _kadparcelList{}.exponentNumber number(3,0), _kadparcelList{}.partNumber varchar(5), _kadparcelList{}.capakey varchar(17), _kadparcelList{}.order varchar(4), _kadparcelList{}.nature varchar(3), _kadparcelList{}.descriptPrivate varchar(35), _kadparcelList{}.block varchar(2), _kadparcelList{}.floor varchar(2), _kadparcelList{}.floorSituation varchar(5), _kadparcelList{}.crossDetail varchar(20), _kadparcelList{}.matUtil varchar(1), _kadparcelList{}.notTaxedMatUtil varchar(3), _kadparcelList{}.nisCom varbinary(6), _kadparcelList{}.street_situation varchar(20), _kadparcelList{}.street_translation varchar(1),
      _kadparcelList{}.street_code varchar(6), _kadparcelList{}.number varchar(6), _kadparcelList{}.polWa varchar(8), _kadparcelList{}.surfaceNotTaxable number(10,0), _kadparcelList{}.surfaceTaxable number(10,0), _kadparcelList{}.surfaceVerif varchar(2), _kadparcelList{}.constructionYear number(5,0), _kadparcelList{}.soilIndex number(2,0), _kadparcelList{}.soilRent varchar(2), _kadparcelList{}.cadastralIncomePerSurface number(3,0), _kadparcelList{}.cadastralIncomePerSurfaceOtherDi number(2,0), _kadparcelList{}.numberCadastralIncome number(1,0), _kadparcelList{}.charCadastralIncome varchar(1), _kadparcelList{}.cadastralIncome number(6,0), _kadparcelList{}.dateEndExoneration varchar(1), _kadparcelList{}.decrete varchar(1), _kadparcelList{}.constructionType varchar(2), _kadparcelList{}.floorNumberAboveground number(2,0), _kadparcelList{}.garret number(2,0), _kadparcelList{}.physModYear number(5,0), _kadparcelList{}.constructionQuality varchar(2), _kadparcelList{}.garageNumber number(2,0), _kadparcelList{}.centralHeating number(2,0), _kadparcelList{}.bathroomNumber number(2,0), _kadparcelList{}.housingUnitNumber number(2,0), _kadparcelList{}.placeNumber number(3,0), _kadparcelList{}.builtSurface number(5,0), _kadparcelList{}.usedSurface number(4,0), _kadparcelList{}.aard varchar(10), _kadparcelList{}.bouwjaar varchar(25),
      _kadparcelList{}.GebouwType varchar(200), _kadparcelList{}.dateSituation varchar(9), ParticHh number(3,0), EenprsHh number(3,0), MeerprsHh number(3,0), GemeensHh number(3,0), GebouwType varchar(150), _gebouweenhList{}.TypeEenh varchar(60), _gebouweenhList{}.Functie varchar(60), _gebouweenhList{}.HandelID varchar(10), _gebouweenhList{}.Domicilie varchar(60), _gebouweenhList{}.CRABadrID varchar(10), _gebouweenhList{}.ParticHh number(3,0), _gebouweenhList{}.EenprsHh number(3,0), _gebouweenhList{}.MeerprsHh number(3,0), _gebouweenhList{}.GemeensHh number(3,0), _gebouweenhList{}.STRAATNMID number(11,0), _gebouweenhList{}.STRAATNM varchar(254), _gebouweenhList{}.HUISNRID number(11,0), _gebouweenhList{}.HUISNR varchar(10), _gebouweenhList{}.HUISNR_BEG varchar(20), _gebouweenhList{}.HUISNR_TIJ varchar(20), _gebouweenhList{}.HUISNR_EIN varchar(20), _gebouweenhList{}.SUBADRESID number(11,0), _gebouweenhList{}.SUBADRES varchar(5), _gebouweenhList{}.SUBADR_BEG varchar(20), _gebouweenhList{}.AARDSUBADR number(11,0), _gebouweenhList{}.NISGEMCODE varchar(5), _gebouweenhList{}.PKANCODE number(11,0), _gebouweenhList{}.GEMNM varchar(4),
      _gebouweenhList{}.AARDADRPOS number(11,0), _gebouweenhList{}.X number(31,15), _gebouweenhList{}.Y number(31,15), _gebouweenhList{}.SUBADR_TIJ varchar(20), _gebouweenhList{}.SUBADR_EIN varchar(20), _gebouweenhList{}.Wooneenh varchar(3), _gebouweenhList{}.GebouwType varchar(150)

Bookmark: OUTPUT: gebouweenheden_adressen
  _huishoudList{}
  _inwList{}
003_Gebouweenheden_Adressen (writer FFS_5)
    attributes: TypeEenh varchar(60), Functie varchar(60), Domicilie varchar(60), CRABadrID varchar(10), capakey varchar(17), ParticHh number(3,0), EenprsHh number(3,0), MeerprsHh number(3,0), GemeensHh number(3,0), HandelID varchar(10), _huishoudList{}.HuishType varchar(60), _huishoudList{}.HuishGrootte number(3,0), _huishoudList{}.GEBDAT varchar(11), _huishoudList{}.GESLACHT varchar(2), _huishoudList{}.NATIONALITEIT number(4,0), _huishoudList{}.VERWERVING number(3,0), _huishoudList{}.REFPERS varchar(2), _huishoudList{}.GEZINSGROOTTE number(3,0), _huishoudList{}.AANTKIND number(3,0), _huishoudList{}.BURGSTAAT varchar(15), _huishoudList{}.NAT_OUD number(4,0), _huishoudList{}.REGISTER varchar(6), _huishoudList{}.BevRegID varchar(10), STRAATNM varchar(255), HUISNR varchar(10), SUBADRES varchar(255), PKANCODE number(11,0), GEMNM varchar(4), Gebouweenh number(3,0), Wooneenh number(3,0),
      GebouwType varchar(150), _inwList{}.STRAATKODE varchar(8), _inwList{}.NUMMER varchar(5), _inwList{}.INDEX varchar(5), _inwList{}.GEBDAT varchar(11), _inwList{}.GESLACHT varchar(2), _inwList{}.NATIONALITEIT number(4,0), _inwList{}.VERWERVING number(3,0), _inwList{}.REFPERS varchar(2), _inwList{}.GEZINSGROOTTE number(3,0), _inwList{}.AANTKIND number(3,0), _inwList{}.BURGSTAAT varchar(15), _inwList{}.NAT_OUD number(4,0), _inwList{}.REGISTER varchar(6), _inwList{}.sector varchar(5), _inwList{}.stadsdeel varchar(16), _inwList{}.wijknaam varchar(30), _inwList{}.gemeensch varchar(12), _inwList{}.BevRegID varchar(10), _inwList{}.CRAB_merge varchar(254), _inwList{}.CRABadrID varchar(10), _inwList{}.GEMNM varchar(4), _inwList{}.PKANCODE number(11,0)

Bookmark: Eigendomsniveau
Note: 999 als Building en appart ingedeeld. Eigenlijk #DEEL (Gebouwen schrijlings op gemeente- of perceelsgrenzen opgericht). Betere categorisering op basis van aard. > uit te werken door elke aard aan 1 vd gebouwtypes toe te kennen

Bookmark: Perceelsniveau
Note: Overige eigendomsinfo op perceelsniveau in ander proces aggregeren en koppelen
Note: Eigenaarsinfo op perceelsniveau en adresniveau in ander proces berekenen en koppelen

Bookmark: Gebouweenheden/adres-locaties
Note: Adressen met domicilie

FME custom transformer ListComparer
Compares the elements of two list attributes. Elements that occur in both lists are written to the output list attribute _both{}. Elements that occur only in one of the lists are written to resp. _onlyfirst{} and _onlysecond{}.
Parameters:
Mode: default
First List Attribute: Specify the first list attribute.
Second List Attribute: Specify the second list attribute.
Both List Name: Specify the name of the list attribute containing the identical elements. (Excluding curly braces {}.)
Only First List Name: Specify the name of the list attribute containing the elements that occur only in the first list. (Excluding curly braces {}.)
Only Second List Name: Specify the name of the list attribute containing the elements that occur only in the first list. (Excluding curly braces {}.) 
Note
Duplicate list elements are compared as individual elements. 
This transformer cannot be applied to
- nested lists; such as "_list{}.sub{}"
- lists missing some elements; such as [<missing>, 1, 2, <missing>, 4, 5]

Parameters:
- MODE = DEFAULT   # Default,DEFAULT Mode
- FIRST_LIST_ATTR =   # " " First List Attribute
- SECOND_LIST_ATTR =   # " " Second List Attribute
- LIST_NAME_BOTHFIRST = _bothfirst   # List Name Both (copy of elements of first list)
- LIST_NAME_ONLYFIRST = _onlyfirst   # List Name OnlyFirst
- LIST_NAME_ONLYSECOND = _onlysecond   # List Name OnlySecond
- LIST_NAME_BOTHSECOND = _bothsecond   # List Name Both (copy of elements of second list)

Input (input)
    -> ParameterFetcher
ParameterFetcher
    ATTR_LIST = listcomparer.mode {$(MODE)} listcomparer.first_list_attr {$(FIRST_LIST_ATTR)} listcomparer.second_list_attr {$(SECOND_LIST_ATTR)}
    -> PythonCaller
PythonCaller
    PYTHONSYMBOL = ListComparer
    PYTHONSOURCE:
      import fmeobjects, locale, re

      class ListComparer(object):
          def __init__(self):
              self.enc = locale.getdefaultlocale()[1]

          def input(self, feature):
              mode = feature.getAttribute('listcomparer.mode')
              list1 = map(str, self.createList(feature, 'listcomparer.first_list_attr'))
              list2 = map(str, self.createList(feature, 'listcomparer.second_list_attr'))
              list1key = feature.getAttribute('listcomparer.first_list_attr')
              list2key = feature.getAttribute('listcomparer.second_list_attr')
              list1name_match = re.match(r'^(.+\{)(\})', list1key)
              list2name_match = re.match(r'^(.+\{)(\})', list2key)
              if not list1name_match:
                  raise fmeobjects.FMEException('listcomparer: Invalid First List Attribute')
              else:
                  list1name = list1name_match.group(1) + list1name_match.group(2)
              if not list2name_match:
                  raise fmeobjects.FMEException('listcomparer: Invalid Second List Attribute')
              else:
                  list2name = list2name_match.group(1) + list2name_match.group(2)

              iboth, ionly1, ionly2 = 0, 0, 0
              if mode == 'DEFAULT':
                  comparelist = []
                  for i, value in enumerate (list(list2)):
                      comparelist.append([value, 'notused'])
                  for i, value in enumerate (list1):
                      src_basename1 = list1name_match.group(1) + '%d' % (i) + '}'
                      alllist1attr = self.getlistattr(feature, list1name, i)
                      if alllist1attr == []:
                          alllist1attr.append('')

                      if ([value, 'notused']) in comparelist:
                          dest_basename1 = 'listcomparer.bothfirst{%d}' % (iboth)
                          dest_basename2 = 'listcomparer.bothsecond{%d}' % (iboth)
                          j = list2.index(value)
                          src_basename2 = list2name_match.group(1) + '%d' % (j) + '}'
                          alllist2attr = self.getlistattr(feature, list2name, j)
                          if alllist2attr == []:
                              alllist2attr.append('')
                          for name in alllist1attr:
                              attrvalue = feature.getAttribute(src_basename1 + name)
                              if attrvalue == None:
                                  feature.setAttributeNullWithType(name, fmeobjects.FME_ATTR_UNDEFINED)
                              else:
                                  feature.setAttribute(dest_basename1 + name, attrvalue)
                          for name in alllist2attr:
                              attrvalue = feature.getAttribute(src_basename2 + name)
                              if attrvalue == None:
                                  feature.setAttributeNullWithType(name, fmeobjects.FME_ATTR_UNDEFINED)
                              else:
                                  feature.setAttribute(dest_basename2 + name, attrvalue)
                          iboth += 1
                          comparelist[comparelist.index([value, 'notused'])][1] ='used'

                      else:
      #                    if value==None:
      #                        print 'None only in list1'
      #                    else:
      #                        print value + 'only in list1'
                          dest_basename = 'listcomparer.onlyfirst{%d}' % (ionly1)
                          for name in alllist1attr:
                              value = feature.getAttribute(src_basename1 + name)
                              if value == None:
                                  feature.setAttributeNullWithType(name, fmeobjects.FME_ATTR_UNDEFINED)
                              else:
                                  feature.setAttribute(dest_basename + name, value)
                          ionly1 += 1

                  list2rev = list(list2)
                  list2rev.reverse()
                  for i, valuelst in enumerate(comparelist):
                      if valuelst[1] == 'notused':
                          value = valuelst[0]
      #                    if value==None:
      #                        print 'None in list2 only'
      #                    else:
      #                        print value + 'in list2 only'
                          src_basename = list2name_match.group(1) + '%d' % (i) + '}'
                          alllistattr = self.getlistattr(feature, list2name, i)
                          if alllistattr == []:
                              alllistattr.append('')

                          dest_basename = 'listcomparer.onlysecond{%d}' % (ionly2)
                          for name in alllistattr:
                              value = feature.getAttribute(src_basename + name)
                              if value == None:
                                  feature.setAttributeNullWithType(name, fmeobjects.FME_ATTR_UNDEFINED)
                              else:
                                  feature.setAttribute(dest_basename + name, value)
                          ionly2 += 1


              elif mode == 'MANYtoONE':
                  comparelist = []
                  for i, value in enumerate (list(list2)):
                      comparelist.append([value, 'notused'])
                  for i, value in enumerate (list1):
                      src_basename1 = list1name_match.group(1) + '%d' % (i) + '}'
                      alllist1attr = self.getlistattr(feature, list1name, i)
                      if alllist1attr == []:
                          alllist1attr.append('')

                      if value in [elem[0] for elem in comparelist]:
                          dest_basename1 = 'listcomparer.bothfirst{%d}' % (iboth)
                          dest_basename2 = 'listcomparer.bothsecond{%d}' % (iboth)
                          j = list2.index(value)
                          src_basename2 = list2name_match.group(1) + '%d' % (j) + '}'
                          alllist2attr = self.getlistattr(feature, list2name, j)
                          if alllist2attr == []:
                              alllist2attr.append('')
                          for name in alllist1attr:
                              attrvalue = feature.getAttribute(src_basename1 + name)
                              if attrvalue == None:
                                  feature.setAttributeNullWithType(name, fmeobjects.FME_ATTR_UNDEFINED)
                              else:
                                  feature.setAttribute(dest_basename1 + name, attrvalue)
                          for name in alllist2attr:
                              attrvalue = feature.getAttribute(src_basename2 + name)
                              if attrvalue == None:
                                  feature.setAttributeNullWithType(name, fmeobjects.FME_ATTR_UNDEFINED)
                              else:
                                  feature.setAttribute(dest_basename2 + name, attrvalue)
                          iboth += 1
                          comparelist[[elem[0] for elem in comparelist].index(value)][1] = 'used'

                      else:
      #                    if value==None:
      #                        print 'None only in list1'
      #                    else:
      #                        print value + 'only in list1'
                          dest_basename = 'listcomparer.onlyfirst{%d}' % (ionly1)
                          for name in alllist1attr:
                              value = feature.getAttribute(src_basename1 + name)
                              if value == None:
                                  feature.setAttributeNullWithType(name, fmeobjects.FME_ATTR_UNDEFINED)
                              else:
                                  feature.setAttribute(dest_basename + name, value)
                          ionly1 += 1

                  list2rev = list(list2)
                  list2rev.reverse()
                  for i, valuelst in enumerate(comparelist):
                      if valuelst[1] == 'notused':
                          value = valuelst[0]
      #                    if value==None:
      #                        print 'None in list2 only'
      #                    else:
      #                        print value + 'in list2 only'
                          src_basename = list2name_match.group(1) + '%d' % (i) + '}'
                          alllistattr = self.getlistattr(feature, list2name, i)
                          if alllistattr == []:
                              alllistattr.append('')

                          dest_basename = 'listcomparer.onlysecond{%d}' % (ionly2)
                          for name in alllistattr:
                              value = feature.getAttribute(src_basename + name)
                              if value == None:
                                  feature.setAttributeNullWithType(name, fmeobjects.FME_ATTR_UNDEFINED)
                              else:
                                  feature.setAttribute(dest_basename + name, value)
                          ionly2 += 1
              else:
                  raise fmeobjects.FMEException('listcomparer: Unsupported Mode')
              self.pyoutput(feature)

          def getlistattr(self, feature, listattrname, index):
              allattr = feature.getAllAttributeNames()
              listattrname_parts = re.match(r'^(.+\{)(\})', listattrname)
              if listattrname_parts:
                  existlistattrnames = []
                  existlistindex = []
                  regex = '(^' + listattrname_parts.group(1) + ')(' + str(index) + ')(' + listattrname_parts.group(2) + ')' + '(\..+)?'
                  for attr in allattr:
                      m = re.match(r'%s' % regex, attr)
                      if m:
                           existlistattrnames.append(m.group(4))
      #                if not(m.group(2) in existlistindex):
      #                     existlistindex.append(m.group(2))
                  return existlistattrnames


          def createList(self, feature, listAttr):
              listName = feature.getAttribute(listAttr)
              if isinstance(listName, unicode):
                  listName = listName.encode(self.enc)
              m = re.match(r'^(.+\{)(\}.*)$', listName)
              s, front, index, back = [], m.group(1), 0, m.group(2)
              listlength = self.getlistlength(feature, listName)
              while index < listlength:
                  name = '%s%d%s' % (front, index, back)
                  isNull, isMissing, type = feature.getAttributeNullMissingAndType(name)
                  if isMissing:
                      s.append(None) #break
                  else:
                      s.append(None if isNull else feature.getAttribute(name))
                  index += 1
              return s

          def getlistlength(self, feature, listAttr):
              allattr = feature.getAllAttributeNames()
              listattrname_parts = re.match(r'^(.+\{)(\})', listAttr)
              if listattrname_parts:
                  existlistindex = []
                  regex = '(^' + listattrname_parts.group(1) + ')(\d+)(' + listattrname_parts.group(2) + ')' + '(\..+)?'
                  for attr in allattr:
                      m = re.match(r'%s' % regex, attr)
                      if m and not(m.group(2) in existlistindex):
                          existlistindex.append(m.group(2))
                  return len(existlistindex)
    NEW_ATTRIBUTES = listcomparer.bothfirst{} listcomparer.bothsecond{} listcomparer.onlyfirst{} listcomparer.onlysecond{}
    -> ListRenamer
ListRenamer
    NEW_LIST_NAME = $(LIST_NAME_BOTHFIRST)
    TYPE = List
    LIST_NAME = listcomparer.bothfirst
    -> ListRenamer_4
ListRenamer_4
    NEW_LIST_NAME = $(LIST_NAME_BOTHSECOND)
    TYPE = List
    LIST_NAME = listcomparer.bothsecond
    -> ListRenamer_2
ListRenamer_2
    NEW_LIST_NAME = $(LIST_NAME_ONLYFIRST)
    TYPE = List
    LIST_NAME = listcomparer.onlyfirst
    -> ListRenamer_3
ListRenamer_3
    NEW_LIST_NAME = $(LIST_NAME_ONLYSECOND)
    TYPE = List
    LIST_NAME = listcomparer.onlysecond
    -> BulkAttributeRemover
BulkAttributeRemover
    ATTR_EXP = ^listcomparer.
    -> Output (output)
Output (output)

FME custom transformer ListAttributeCreator
Adds a listattribute to an existing list, supplying them with constants, attribute values, and expressions. Any feature that enters the transformer and contains the given list, emerges with a the attribute as defined in the transformer’s parameters dialog.
Parameters:
Mode: default
List Attribute Name: Specify the name of the new list attribute. Attributes can only be added to existing lists. Ex. '_existinglist{}._newattribute'.
Value: Specify the value of the new listattribute. 
Note
Duplicate list elements are compared as individual elements. 
This transformer cannot be applied to
- nested lists; such as "_list{}.sub{}"
- lists missing some elements; such as [<missing>, 1, 2, <missing>, 4, 5]

Parameters:
- MODE = DEFAULT   # Copy Attribute to ListAttribute,DEFAULT%Create Attribute with Value Expression,EXPR Mode
- LIST_ATTR_NAME =   # List Attribute Name
- ATTR_VALUE =   # " " Attribute Value
- VALUE_EXPR =   # Value expression

Input (input)
    -> AttributeCreator
AttributeCreator
    ATTR_LIST = listattrcreator.value,$(ATTR_VALUE)
    -> ParameterFetcher_2
ParameterFetcher_2
    ATTR_LIST = listattrcreator.mode {$(MODE)} listattrcreator.listattrname {$(LIST_ATTR_NAME)} listattrcreator.value_expr {$(VALUE_EXPR)}
    -> PythonCaller
PythonCaller
    PYTHONSYMBOL = ListAttributeCreator
    PYTHONSOURCE:
      import fmeobjects, locale, re

      class ListAttributeCreator(object):
          def __init__(self):
              self.enc = locale.getdefaultlocale()[1]

          def input(self, feature):
              logger = fmeobjects.FMELogFile()

              mode = feature.getAttribute('listattrcreator.mode')
              listattrname = feature.getAttribute('listattrcreator.listattrname')
              if mode == 'DEFAULT':
                  value = feature.getAttribute('listattrcreator.value')
              else:
                  value = feature.getAttribute('listattrcreator.value_expr') #mode == 'EXPR'
              allattr = feature.getAllAttributeNames()
              listattrname_parts = re.match(r'^(.+\{)(\d*)(\})\.(.+)', listattrname)
              if listattrname_parts:
                  try:
                      i = int(listattrname_parts.group(2))
                      listlength = i + 1
      #            existlistindex = []
      #            regex = '(^' + listattrname_parts.group(1) + ')(\d+)(' + listattrname_parts.group(2) + ')'
      #            existlistattrnames = []

      #            for attr in allattr:
      #                m = re.match(r'%s' % regex, attr)
      #                if m:
      #                    if m.group(2) == 0:
      #                        existlistattrnames.append(m.group(1))
      #                    if not(m.group(2) in existlistindex):
      #                        existlistindex.append(m.group(2))
      #            logger.logMessageString('indexlist ' + str(len(existlistindex)) + ' items')
                  except:
                      listlength = self.getlistlength(feature, listattrname)
                      i = 0
                  while i < listlength:
                      if mode == 'DEFAULT':
                          name = listattrname_parts.group(1) + '%d' % i + listattrname_parts.group(3) + '.' + listattrname_parts.group(4)
                          if value == None:
                              feature.setAttributeNullWithType(name, fmeobjects.FME_ATTR_UNDEFINED)
                          else:
                              feature.setAttribute(name, value)
                      else: #mode == 'EXPR'
                      # value (numeric)
                          pattern = re.compile(r'([^@]*)@attrValue\(([^\)]+)\)([^@]*)')
                          expr = ''
                          if not re.match(pattern, value):
                              expr = value
                          for (before, valueattrname, after) in re.findall(pattern, value):
                              valueattrname_list = re.match(r'^(.+\{)(\}.*)', valueattrname)
                              if valueattrname_list:
                                  name = valueattrname_list.group(1) + '%d' % i + valueattrname_list.group(2)
                              else:
                                  name = valueattrname
                              attrvalue = feature.getAttribute(name)
                              expr = expr + before + str(attrvalue) + after
                          try: result = eval(expr)
                          except: result = expr
                      # write
                          name = listattrname_parts.group(1) + '%d' % i + listattrname_parts.group(3) + '.' + listattrname_parts.group(4)
                          if result == None:
                              feature.setAttributeNullWithType(name, fmeobjects.FME_ATTR_UNDEFINED)
                          else:
                              feature.setAttribute(name, result)
      #                    logger.logMessageString(str(result))
                      i += 1


              self.pyoutput(feature)

          def createList(self, feature, listAttr):
              listName = feature.getAttribute(listAttr)
              if isinstance(listName, unicode):
                  listName = listName.encode(self.enc)
              m = re.match(r'^(.+\{)(\}.*)$', listName)
              s, front, index, back = [], m.group(1), 0, m.group(2)
              listlength = self.getlistlength(feature, listName)
              while index < listlength:
                  name = '%s%d%s' % (front, index, back)
                  isNull, isMissing, type = feature.getAttributeNullMissingAndType(name)
                  if isMissing:
                      s.append(None) #break
                  else:
                      s.append(None if isNull else feature.getAttribute(name))
                  index += 1
              return s

          def getlistlength(self, feature, listAttr):
              allattr = feature.getAllAttributeNames()
              listattrname_parts = re.match(r'^(.+\{)(\})', listAttr)
              if listattrname_parts:
                  existlistindex = []
                  regex = '(^' + listattrname_parts.group(1) + ')(\d+)(' + listattrname_parts.group(2) + ')' + '(\..+)?'
                  for attr in allattr:
                      m = re.match(r'%s' % regex, attr)
                      if m and not(m.group(2) in existlistindex):
                          existlistindex.append(m.group(2))
                  return len(existlistindex)





      #    def createList(self, feature, listAttr):
      #        if listAttr != '':
      #        listName = feature.getAttribute(listAttr)
      #        elif listName != '':
      #            listName = listName
      #        else:
      #            raise fmeobjects.FMEException('TargetedOverlayer: Unsupported ListAttribute or Listname')
      #
      #        if isinstance(listName, unicode):
      #            listName = listName.encode(self.enc)
      #        m = re.match(r'^(.+\{)(\}.*)$', listName)
      #        s, front, index, back = [], m.group(1), 0, m.group(2)
      #        while True:
      #            name = '%s%d%s' % (front, index, back)
      #            isNull, isMissing, type = feature.getAttributeNullMissingAndType(name)
      #            if isMissing:
      #                break
      #            else:
      #                s.append(None if isNull else feature.getAttribute(name))
      #            index += 1
      #        return s
    -> BulkAttributeRemover
BulkAttributeRemover
    ATTR_EXP = ^listattrcreator.
    -> Output (output)
Output (output)

FME custom transformer ListFilter
Filters list elements by test condition to new filtered lists.

Parameters:
- MODE = DEFAULT   # Default,DEFAULT Mode
- LIST_ATTR =   # " " List Attribute to filter
- FILTER_VALUES =   # Filter Values (comma delimited)
- RESULTLIST_BASE = _filterlist   # Basename of resulting filtered lists
- RESULTLIST_SUFFIXLENGTH = 15   # Max length of resultlist suffix

Input (input)
    -> ParameterFetcher
ParameterFetcher
    ATTR_LIST = listfilter.mode {$(MODE)} listfilter.list_attr {$(LIST_ATTR)} listfilter.filter_values {$(FILTER_VALUES)} listfilter.resultlist_base {$(RESULTLIST_BASE)} listfilter.suffixlength {$(RESULTLIST_SUFFIXLENGTH)}
    -> PythonCaller
PythonCaller
    PYTHONSYMBOL = ListFilter
    PYTHONSOURCE:
      import fmeobjects, locale, re

      class ListFilter(object):
          def __init__(self):
              self.enc = locale.getdefaultlocale()[1]

          def input(self, feature):
              mode = feature.getAttribute('listfilter.mode')
              listattr_input = feature.getAttribute('listfilter.list_attr')
              listname_match = re.match(r'^(.+{)\d*(\})(\.)?(.+)?$', listattr_input)
              filter_values = feature.getAttribute('listfilter.filter_values').split(',')
              resultlist_base = feature.getAttribute('listfilter.resultlist_base')
              suffixlength = int(feature.getAttribute('listfilter.suffixlength'))
              # get list of values to filter
              if not listname_match:
                  raise fmeobjects.FMEException('listfilter: Invalid List Attribute')
              else:
                  listname = listname_match.group(1) + listname_match.group(2)
      #            listattr = ''
      #            i = 1
      #            while i <=4:
      #                if listname_match.group(i):
      #                    listattr += listname_match.group(i)
      #                i+=1
                  filterlist = self.createList(feature, 'listfilter.list_attr')


              if mode == 'DEFAULT':
                  # get names of resulting filtered lists
                  filterlist_names = {}
                  indexdict = {}
                  for i, value in enumerate(filter_values):
                      name = str(value[0:suffixlength]).replace(' ','_')
                      if name in indexdict:
                          indexdict[name] += 1
                          name = name[0:suffixlength-2] + '{0:0>2}'.format(indexdict[name])
                      else:
                          indexdict[name] = 0
                      filterlist_names[value] = name
                  filterlist_names['unfiltered'] = 'unfiltered'
                  # set indexes of resulting filtered lists to 0
                  idest = {}
                  for value in filterlist_names:
                      idest[filterlist_names[value]] = 0

                  # append listelement to filtered lists
                  for i, value in enumerate(filterlist):
                      if value in filterlist_names:
                          name = filterlist_names[value]
                      else:
                          name = 'unfiltered'
                      dest_basename = resultlist_base + '.' + name + '{' + '%d' % idest[name] + '}'
                      idest[name] += 1
                      src_basename = listname_match.group(1) + '%d' % i + '}'
                      alllistattr = self.getlistattr(feature, listname, i)
                      if alllistattr ==  []:
                          alllistattr.append('')
                      for attr in alllistattr:
                          attrvalue = feature.getAttribute(src_basename + attr)
                          if attrvalue == None:
                              feature.setAttributeNullWithType(attr, fmeobjects.FME_ATTR_UNDEFINED)
                          else:
                              feature.setAttribute(dest_basename + attr, attrvalue)

              else:
                  raise fmeobjects.FMEException('listfilter: Unsupported Mode')
              self.pyoutput(feature)


          def getlistattr(self, feature, listattrname, index):
              allattr = feature.getAllAttributeNames()
              listattrname_parts = re.match(r'^(.+\{)(\})', listattrname)
              if listattrname_parts:
                  existlistattrnames = []
                  existlistindex = []
                  regex = '(^' + listattrname_parts.group(1) + ')(' + str(index) + ')(' + listattrname_parts.group(2) + ')' + '(\..+)?'
                  for attr in allattr:
                      m = re.match(r'%s' % regex, attr)
                      if m:
                           existlistattrnames.append(m.group(4))
      #                if not(m.group(2) in existlistindex):
      #                     existlistindex.append(m.group(2))
                  return existlistattrnames


          def createList(self, feature, listAttr):
              listName = feature.getAttribute(listAttr)
              if isinstance(listName, unicode):
                  listName = listName.encode(self.enc)
              m = re.match(r'^(.+\{)(\}.*)$', listName)
              s, front, index, back = [], m.group(1), 0, m.group(2)
              listlength = self.getlistlength(feature, listName)
              while index < listlength:
                  name = '%s%d%s' % (front, index, back)
                  isNull, isMissing, type = feature.getAttributeNullMissingAndType(name)
                  if isMissing:
                      s.append(None) #break
                  else:
                      s.append(None if isNull else feature.getAttribute(name))
                  index += 1
              return s

          def getlistlength(self, feature, listAttr):
              allattr = feature.getAllAttributeNames()
              listattrname_parts = re.match(r'^(.+\{)(\})', listAttr)
              if listattrname_parts:
                  existlistindex = []
                  regex = '(^' + listattrname_parts.group(1) + ')(\d+)(' + listattrname_parts.group(2) + ')' + '(\..+)?'
                  for attr in allattr:
                      m = re.match(r'%s' % regex, attr)
                      if m and not(m.group(2) in existlistindex):
                          existlistindex.append(m.group(2))
                  return len(existlistindex)
    -> Output (output)
Output (output)
BulkAttributeRenamer
    PATTERN_ACTION_DISP = Add String Prefix
    CASE_CHANGE_TYPE = UPPERCASE
    ATTRCHOICE = All Attributes
    CASE_DISP = yes
ListRenamer
    NEW_LIST_NAME = $(RESULTLIST_BASE)
    TYPE = List
    LIST_NAME = listcomparer.bothfirst
    -> ListRenamer_4
ListRenamer_4
    NEW_LIST_NAME = _bothsecond
    TYPE = List
    LIST_NAME = listcomparer.bothsecond
    -> ListRenamer_2
ListRenamer_2
    NEW_LIST_NAME = _onlyfirst
    TYPE = List
    LIST_NAME = listcomparer.onlyfirst
    -> ListRenamer_3
ListRenamer_3
    NEW_LIST_NAME = _onlysecond
    TYPE = List
    LIST_NAME = listcomparer.onlysecond
    -> BulkAttributeRemover
BulkAttributeRemover
    ATTR_EXP = ^listcomparer.
