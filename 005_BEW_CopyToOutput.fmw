FME workspace 005_BEW_CopyToOutput.fmw
Title: 005_BEW_CopyToOutput
Description: Bewerkingen: 
Kopiëren en hernoemen van definitieve resultaten naar output.
History: 2016-10-06,Jonas Verstraete,Initial version,2016-10-21,Jonas Verstraete,Update new cadastre data structure

Parameters:
- SourceDataset_FFS = ..\data\intermediate\001\001_BevReg_CRAB.ffs   # Source FME Feature Store (FFS) File(s)
- SourceDataset_FFS_9 = ..\data\intermediate\003\003_Huishoudens.ffs   # Source FME Feature Store (FFS) File(s)
- SourceDataset_FFS_13 = ..\data\intermediate\002\002_CRAB_alladr_capakey.ffs   # Source FME Feature Store (FFS) File(s)
- DestDataset_FFS = ..\data\output\BEW_Inwoners.ffs   # Destination FME Feature Store (FFS) File
- DestDataset_ESRISHAPE = ..\data\output   # Destination Esri Shapefile Folder
- DestDataset_FFS_2 = ..\data\output\BEW_Huishoudens.ffs   # Destination FME Feature Store (FFS) File
- DestDataset_FFS_3 = ..\data\output\BEW_Adressen.ffs   # Destination FME Feature Store (FFS) File
- DestDataset_FFS_4 = ..\data\output\BEW_Gebouweenheden_Adressen.ffs   # Destination FME Feature Store (FFS) File
- DestDataset_FFS_5 = ..\data\output\BEW_Percelen.ffs   # Destination FME Feature Store (FFS) File
- DestDataset_FFS_6 = ..\data\output\BEW_Eigendommen.ffs   # Destination FME Feature Store (FFS) File
- DestDataset_FFS_11 = ..\data\output\BEW_Eigenaars.ffs   # Destination FME Feature Store (FFS) File
- SourceDataset_FFS_14 = ..\data\intermediate\004\004_Gebouweenheden_Adressen.ffs   # Source FME Feature Store (FFS) File(s)
- SourceDataset_FFS_10 = ..\data\intermediate\004\004_KAD_percelen.ffs   # Source FME Feature Store (FFS) File(s)
- SourceDataset_FFS_11 = ..\data\intermediate\000\000_KAD.ffs   # Source FME Feature Store (FFS) File(s)
- SourceDataset_FFS_8 = ..\data\intermediate\004\004_KAD_owner.ffs   # Source FME Feature Store (FFS) File(s)

Readers:
- FFS_1: FFS from $(SourceDataset_FFS)
- FFS_2: FFS from $(SourceDataset_FFS_9)
- FFS_3: FFS from $(SourceDataset_FFS_13)
- FFS_4: FFS from $(SourceDataset_FFS_14)
- FFS_5: FFS from $(SourceDataset_FFS_10)
- FFS_6: FFS from $(SourceDataset_FFS_11)
- FFS_7: FFS from $(SourceDataset_FFS_8)

Writers:
- FFS_8: FFS to $(DestDataset_FFS) in EPSG:31370
- ESRISHAPE_1: ESRISHAPE to $(DestDataset_ESRISHAPE)
- FFS_9: FFS to $(DestDataset_FFS_2) in EPSG:31370
- FFS_10: FFS to $(DestDataset_FFS_3) in EPSG:31370
- FFS_11: FFS to $(DestDataset_FFS_4) in EPSG:31370
- FFS_12: FFS to $(DestDataset_FFS_5) in EPSG:31370
- FFS_13: FFS to $(DestDataset_FFS_6) in EPSG:31370
- FFS_14: FFS to $(DestDataset_FFS_11) in EPSG:31370

Note: 005_BEW_CopyToOutput.fmw / Bewerkingen: / Kopiëren en hernoemen van definitieve resultaten naar output.
001_BevReg_CRAB (reader FFS_1)
    attributes: POSTKODE varchar(4), STRAATKODE varchar(8), NUMMER varchar(5), INDEX varchar(5), GEBDAT varchar(11), GESLACHT varchar(2), NATIONALITEIT number(4,0), VERWERVING number(3,0), REFPERS varchar(2), GEZINSGROOTTE number(3,0), AANTKIND number(3,0), BURGSTAAT varchar(15), NAT_OUD number(4,0), REGISTER varchar(6), sector varchar(5), stadsdeel varchar(16), wijknaam varchar(30), gemeensch varchar(12), BevRegID varchar(10), CRAB_merge varchar(254), CRABadrID varchar(10), GEMNM varchar(4), HUISNR varchar(10), PKANCODE number(11,0), STRAATNM varchar(255), SUBADRES varchar(255)
    -> BEW_Inwoners (writer FFS_8)
    -> AttributeRenamer
BEW_Inwoners (writer FFS_8)
    attributes: POSTKODE varchar(4), STRAATKODE varchar(8), NUMMER varchar(5), INDEX varchar(5), GEBDAT varchar(11), GESLACHT varchar(2), NATIONALITEIT number(4,0), VERWERVING number(3,0), REFPERS varchar(2), GEZINSGROOTTE number(3,0), AANTKIND number(3,0), BURGSTAAT varchar(15), NAT_OUD number(4,0), REGISTER varchar(6), sector varchar(5), stadsdeel varchar(16), wijknaam varchar(30), gemeensch varchar(12), BevRegID varchar(10), CRAB_merge varchar(254), CRABadrID varchar(10), GEMNM varchar(4), HUISNR varchar(10), PKANCODE number(11,0), STRAATNM varchar(255), SUBADRES varchar(255)
AttributeRenamer
    ATTR_TABLE:
      RENAME_SET_DEFAULT NATIONALITEIT > NATIONALIT
      RENAME_SET_DEFAULT GEZINSGROOTTE > GEZINSGROO
    -> BEW_Inwoners (writer ESRISHAPE_1)
BEW_Inwoners (writer ESRISHAPE_1)
    attributes: POSTKODE char(4), STRAATKODE char(8), NUMMER char(5), INDEX char(5), GEBDAT char(11), GESLACHT char(2), NATIONALIT number(4,0), VERWERVING number(3,0), REFPERS char(2), GEZINSGROO number(3,0), AANTKIND number(3,0), BURGSTAAT char(15), NAT_OUD number(4,0), REGISTER char(6), sector char(5), stadsdeel char(16), wijknaam char(30), gemeensch char(12), BevRegID char(10), CRAB_merge char(254), CRABadrID char(10), GEMNM char(4), HUISNR char(10), PKANCODE number(11,0), STRAATNM char(255), SUBADRES char(255)
003_Huishoudens (reader FFS_2)
    attributes: POSTKODE varchar(4), STRAATKODE varchar(8), NUMMER varchar(5), INDEX varchar(5), GEBDAT varchar(11), GESLACHT varchar(2), NATIONALITEIT number(4,0), VERWERVING number(3,0), REFPERS varchar(2), GEZINSGROOTTE number(3,0), AANTKIND number(3,0), BURGSTAAT varchar(15), NAT_OUD number(4,0), REGISTER varchar(6), sector varchar(5), stadsdeel varchar(16), wijknaam varchar(30), BevRegID varchar(10), CRAB_merge varchar(254), CRABadrID varchar(10), GEMNM varchar(4), STRAATNM varchar(255), HUISNR varchar(10), PKANCODE number(11,0), SUBADRES varchar(255), capakey varchar(30), HuishGrootte number(10,0), HuishType varchar(60)
    -> BEW_Huishoudens (writer FFS_9)
    -> AttributeRenamer_2
BEW_Huishoudens (writer FFS_9)
    attributes: POSTKODE varchar(4), STRAATKODE varchar(8), NUMMER varchar(5), INDEX varchar(5), GEBDAT varchar(11), GESLACHT varchar(2), NATIONALITEIT number(4,0), VERWERVING number(3,0), REFPERS varchar(2), GEZINSGROOTTE number(3,0), AANTKIND number(3,0), BURGSTAAT varchar(15), NAT_OUD number(4,0), REGISTER varchar(6), sector varchar(5), stadsdeel varchar(16), wijknaam varchar(30), BevRegID varchar(10), CRAB_merge varchar(254), CRABadrID varchar(10), GEMNM varchar(4), STRAATNM varchar(255), HUISNR varchar(10), PKANCODE number(11,0), SUBADRES varchar(255), capakey varchar(30), HuishGrootte number(10,0), HuishType varchar(60)
AttributeRenamer_2
    ATTR_TABLE:
      RENAME_SET_DEFAULT NATIONALITEIT > NATIONALIT
      RENAME_SET_DEFAULT GEZINSGROOTTE > GEZINSGROO
      RENAME_SET_DEFAULT HuishGrootte > HuishGroot
    -> BEW_Huishoudens (writer ESRISHAPE_1)
BEW_Huishoudens (writer ESRISHAPE_1)
    attributes: POSTKODE char(4), STRAATKODE char(8), NUMMER char(5), INDEX char(5), GEBDAT char(11), GESLACHT char(2), NATIONALIT number(4,0), VERWERVING number(3,0), REFPERS char(2), GEZINSGROO number(3,0), AANTKIND number(3,0), BURGSTAAT char(15), NAT_OUD number(4,0), REGISTER char(6), sector char(5), stadsdeel char(16), wijknaam char(30), BevRegID char(10), CRAB_merge char(254), CRABadrID char(10), GEMNM char(4), STRAATNM char(255), HUISNR char(10), PKANCODE number(11,0), SUBADRES char(255), capakey char(30), HuishGroot number(10,0), HuishType char(60)
002_CRAB_alladr_capakey (reader FFS_3)
    attributes: CRABadrID varchar(10), STRAATNMID number(11,0), STRAATNM varchar(255), HUISNRID number(11,0), HUISNR varchar(10), HUISNR_BEG varchar(20), HUISNR_TIJ varchar(20), HUISNR_EIN varchar(20), SUBADRESID number(11,0), SUBADRES varchar(255), SUBADR_BEG varchar(20), AARDSUBADR number(11,0), NISGEMCODE varchar(5), PKANCODE number(11,0), GEMNM varchar(4), AARDADRPOS number(11,0), X number(31,15), Y number(31,15), SUBADR_TIJ varchar(20), SUBADR_EIN varchar(20), Type varchar(150), Omschrijving varchar(150), CAPAKEY varchar(30), CRABcapa varchar(30), geoCAPAKEY varchar(30)
    -> AttributeRenamer_3
AttributeRenamer_3
    ATTR_TABLE:
      RENAME_SET_DEFAULT Type > CaPaType
      RENAME_SET_DEFAULT Omschrijving > CaPaOmschr
    -> AttributeCreator
AttributeCreator
    ATTR_TABLE = SET_TO AdrType = FME_CONDITIONAL:DEFAULT_VALUE'CRAB adres'BOOL_OP;OR;COMPOSITE_TEST;<Unused>;TEST @Value(CRABadrID) LIKE HFD%'BevReg adres - CRAB hoofdadres (merged to CRAB hoofdadres)'BOOL_OP;OR;COMPOSITE_TEST;<Unused>;TEST @Value(CRABadrID) LIKE COR%'BevReg adres - COR CRAB hoofdadres (corrected by geolocator and merged to CRAB hoofdadres)'BOOL_OP;OR;COMPOSITE_TEST;<Unused>;TEST @Value(CRABadrID) LIKE GL%'BevReg adres - GL CRAB hoofdadres (CRAB hoofdadrespositie by geolocator)'FME_NUM_CONDITIONS4___
    -> BEW_Adressen (writer FFS_10)
    -> BEW_Adressen (writer ESRISHAPE_1)
BEW_Adressen (writer FFS_10)
    attributes: CRABadrID varchar(10), STRAATNMID number(11,0), STRAATNM varchar(255), HUISNRID number(11,0), HUISNR varchar(10), HUISNR_BEG varchar(20), HUISNR_TIJ varchar(20), HUISNR_EIN varchar(20), SUBADRESID number(11,0), SUBADRES varchar(255), SUBADR_BEG varchar(20), AARDSUBADR number(11,0), NISGEMCODE varchar(5), PKANCODE number(11,0), GEMNM varchar(4), AARDADRPOS number(11,0), X number(31,15), Y number(31,15), SUBADR_TIJ varchar(20), SUBADR_EIN varchar(20), AdrType varchar(100), CaPaType varchar(150), CaPaOmschr varchar(150), CAPAKEY varchar(30), CRABcapa varchar(30), geoCAPAKEY varchar(30)
BEW_Adressen (writer ESRISHAPE_1)
    attributes: CRABadrID char(10), STRAATNMID number(11,0), STRAATNM char(255), HUISNRID number(11,0), HUISNR char(10), HUISNR_BEG char(20), HUISNR_TIJ char(20), HUISNR_EIN char(20), SUBADRESID number(11,0), SUBADRES char(255), SUBADR_BEG char(20), AARDSUBADR number(11,0), NISGEMCODE char(5), PKANCODE number(11,0), GEMNM char(4), AARDADRPOS number(11,0), X number(31,15), Y number(31,15), SUBADR_TIJ char(20), SUBADR_EIN char(20), AdrType char(100), CaPaType char(150), CaPaOmschr char(150), CAPAKEY char(30), CRABcapa char(30), geoCAPAKEY char(30)
004_Gebouweenheden_Adressen (reader FFS_4)
    attributes: TypeEenh varchar(60), Functie varchar(60), Domicilie varchar(60), CRABadrID varchar(10), capakey varchar(17), ParticHh number(3,0), EenprsHh number(3,0), MeerprsHh number(3,0), GemeensHh number(3,0), HandelID varchar(10), _huishoudList{}.HuishType varchar(60), _huishoudList{}.HuishGrootte number(3,0), _huishoudList{}.GEBDAT varchar(11), _huishoudList{}.GESLACHT varchar(2), _huishoudList{}.NATIONALITEIT number(4,0), _huishoudList{}.VERWERVING number(3,0), _huishoudList{}.REFPERS varchar(2), _huishoudList{}.GEZINSGROOTTE number(3,0), _huishoudList{}.AANTKIND number(3,0), _huishoudList{}.BURGSTAAT varchar(15), _huishoudList{}.NAT_OUD number(4,0), _huishoudList{}.REGISTER varchar(6), _huishoudList{}.BevRegID varchar(10), STRAATNM varchar(255), HUISNR varchar(10), SUBADRES varchar(255), PKANCODE number(11,0), GEMNM varchar(4), Gebouweenh number(3,0), Wooneenh number(3,0),
      GebouwType varchar(150), _inwList{}.STRAATKODE varchar(8), _inwList{}.NUMMER varchar(5), _inwList{}.INDEX varchar(5), _inwList{}.GEBDAT varchar(11), _inwList{}.GESLACHT varchar(2), _inwList{}.NATIONALITEIT number(4,0), _inwList{}.VERWERVING number(3,0), _inwList{}.REFPERS varchar(2), _inwList{}.GEZINSGROOTTE number(3,0), _inwList{}.AANTKIND number(3,0), _inwList{}.BURGSTAAT varchar(15), _inwList{}.NAT_OUD number(4,0), _inwList{}.REGISTER varchar(6), _inwList{}.sector varchar(5), _inwList{}.stadsdeel varchar(16), _inwList{}.wijknaam varchar(30), _inwList{}.gemeensch varchar(12), _inwList{}.BevRegID varchar(10), _inwList{}.CRAB_merge varchar(254), _inwList{}.CRABadrID varchar(10), _inwList{}.GEMNM varchar(4), _inwList{}.PKANCODE number(11,0), EigWoning varchar(30), InwEigenaars number(4,0), _inwEigenaarsList{}.officialId varchar(12), _inwEigenaarsList{}.name varchar(80), _inwEigenaarsList{}.firstname varchar(12), _inwEigenaarsList{}.birthdate varchar(11), _inwEigenaarsList{}.country varchar(3),
      _inwEigenaarsList{}.zipCode varchar(4), _inwEigenaarsList{}.municipality_fr varchar(30), _inwEigenaarsList{}.municipality_nl varchar(30), _inwEigenaarsList{}.street_fr varchar(30), _inwEigenaarsList{}.street_nl varchar(30), _inwEigenaarsList{}.number varchar(5), _inwEigenaarsList{}.boxNumber varchar(5), _inwEigenaarsList{}.officialId_partner varchar(13), _inwEigenaarsList{}.name_partner varchar(23), _inwEigenaarsList{}.firstName_partner varchar(13), _inwEigenaarsList{}.birthdate_partner varchar(11), _inwEigenaarsList{}.country_partner varchar(3), _inwEigenaarsList{}.zipCode_partner varchar(5), _inwEigenaarsList{}.municipality_partner_fr varchar(30), _inwEigenaarsList{}.municipality_partner_nl varchar(30), _inwEigenaarsList{}.street_partner_fr varchar(30), _inwEigenaarsList{}.street_partner_nl varchar(30), _inwEigenaarsList{}.number_partner varchar(20), _inwEigenaarsList{}.boxNumber_partner varchar(5), _inwEigenaarsList{}.coOwner varchar(16), _inwEigenaarsList{}.anonymousOwner varchar(1), _inwEigenaarsList{}.CRABadrID varchar(10), _inwOwnerList{}.propertySituationIdf varchar(9), _inwOwnerList{}.order varchar(3), _inwOwnerList{}.partyType varchar(3), _inwOwnerList{}.right varchar(51), _inwOwnerList{}.right_trad varchar(51), _inwOwnerList{}.managedBy number(2,0), _inwOwnerList{}.officialId varchar(12), _inwOwnerList{}.name varchar(80),
      _inwOwnerList{}.firstname varchar(12), _inwOwnerList{}.birthdate varchar(11), _inwOwnerList{}.country varchar(3), _inwOwnerList{}.zipCode varchar(4), _inwOwnerList{}.municipality_fr varchar(30), _inwOwnerList{}.municipality_nl varchar(30), _inwOwnerList{}.street_fr varchar(30), _inwOwnerList{}.street_nl varchar(30), _inwOwnerList{}.number varchar(5), _inwOwnerList{}.boxNumber varchar(5), _inwOwnerList{}.officialId_partner varchar(13), _inwOwnerList{}.name_partner varchar(23), _inwOwnerList{}.firstName_partner varchar(13), _inwOwnerList{}.birthdate_partner varchar(11), _inwOwnerList{}.country_partner varchar(3), _inwOwnerList{}.zipCode_partner varchar(5), _inwOwnerList{}.municipality_partner_fr varchar(30), _inwOwnerList{}.municipality_partner_nl varchar(30), _inwOwnerList{}.street_partner_fr varchar(30), _inwOwnerList{}.street_partner_nl varchar(30), _inwOwnerList{}.number_partner varchar(20), _inwOwnerList{}.boxNumber_partner varchar(5), _inwOwnerList{}.anonymousOwner varchar(1), _inwOwnerList{}.coOwner varchar(16), _inwOwnerList{}.dateSituation varchar(9), _inwOwnerList{}.CRABadrID varchar(10), _inwParcelList{}.constructionIndication number(4,0), _inwParcelList{}.propertySituationIdf number(8,0), _inwParcelList{}.divCad number(5,0), _inwParcelList{}.section varchar(1),
      _inwParcelList{}.primaryNumber number(3,0), _inwParcelList{}.bisNumber number(2,0), _inwParcelList{}.exponentLetter varchar(1), _inwParcelList{}.exponentNumber number(3,0), _inwParcelList{}.partNumber varchar(5), _inwParcelList{}.capakey varchar(17), _inwParcelList{}.order varchar(4), _inwParcelList{}.nature varchar(3), _inwParcelList{}.descriptPrivate varchar(35), _inwParcelList{}.block varchar(2), _inwParcelList{}.floor varchar(2), _inwParcelList{}.floorSituation varchar(5), _inwParcelList{}.crossDetail varchar(20), _inwParcelList{}.matUtil varchar(1), _inwParcelList{}.notTaxedMatUtil varchar(3), _inwParcelList{}.nisCom varchar(6), _inwParcelList{}.street_situation varchar(20), _inwParcelList{}.street_translation varchar(1), _inwParcelList{}.street_code varchar(6), _inwParcelList{}.number varchar(6), _inwParcelList{}.polWa varchar(8), _inwParcelList{}.surfaceNotTaxable number(10,0), _inwParcelList{}.surfaceTaxable number(10,0), _inwParcelList{}.surfaceVerif varchar(2), _inwParcelList{}.constructionYear number(5,0), _inwParcelList{}.soilIndex number(2,0), _inwParcelList{}.soilRent varchar(2), _inwParcelList{}.cadastralIncomePerSurface number(3,0), _inwParcelList{}.cadastralIncomePerSurfaceOtherDi number(2,0), _inwParcelList{}.numberCadastralIncome number(1,0),
      _inwParcelList{}.charCadastralIncome varchar(1), _inwParcelList{}.cadastralIncome number(6,0), _inwParcelList{}.dateEndExoneration varchar(1), _inwParcelList{}.decrete varchar(1), _inwParcelList{}.constructionType varchar(2), _inwParcelList{}.floorNumberAboveground number(2,0), _inwParcelList{}.garret number(2,0), _inwParcelList{}.physModYear number(5,0), _inwParcelList{}.constructionQuality varchar(2), _inwParcelList{}.garageNumber number(2,0), _inwParcelList{}.centralHeating number(2,0), _inwParcelList{}.bathroomNumber number(2,0), _inwParcelList{}.housingUnitNumber number(2,0), _inwParcelList{}.placeNumber number(3,0), _inwParcelList{}.builtSurface number(5,0), _inwParcelList{}.usedSurface number(4,0), _inwParcelList{}.dateSituation varchar(9), _inwParcelList{}.aard varchar(10), _inwParcelList{}.bouwjaar varchar(25), _inwParcelList{}.GebouwType varchar(200)
    -> BEW_Gebouweenheden_Adressen (writer FFS_11)
    -> AttributeRenamer_4
BEW_Gebouweenheden_Adressen (writer FFS_11)
    attributes: TypeEenh varchar(60), Functie varchar(60), Domicilie varchar(60), CRABadrID varchar(10), capakey varchar(17), ParticHh number(3,0), EenprsHh number(3,0), MeerprsHh number(3,0), GemeensHh number(3,0), HandelID varchar(10), _huishoudList{}.HuishType varchar(60), _huishoudList{}.HuishGrootte number(3,0), _huishoudList{}.GEBDAT varchar(11), _huishoudList{}.GESLACHT varchar(2), _huishoudList{}.NATIONALITEIT number(4,0), _huishoudList{}.VERWERVING number(3,0), _huishoudList{}.REFPERS varchar(2), _huishoudList{}.GEZINSGROOTTE number(3,0), _huishoudList{}.AANTKIND number(3,0), _huishoudList{}.BURGSTAAT varchar(15), _huishoudList{}.NAT_OUD number(4,0), _huishoudList{}.REGISTER varchar(6), _huishoudList{}.BevRegID varchar(10), STRAATNM varchar(255), HUISNR varchar(10), SUBADRES varchar(255), PKANCODE number(11,0), GEMNM varchar(4), GebouwType varchar(150), _inwList{}.STRAATKODE varchar(8),
      _inwList{}.NUMMER varchar(5), _inwList{}.INDEX varchar(5), _inwList{}.GEBDAT varchar(11), _inwList{}.GESLACHT varchar(2), _inwList{}.NATIONALITEIT number(4,0), _inwList{}.VERWERVING number(3,0), _inwList{}.REFPERS varchar(2), _inwList{}.GEZINSGROOTTE number(3,0), _inwList{}.AANTKIND number(3,0), _inwList{}.BURGSTAAT varchar(15), _inwList{}.NAT_OUD number(4,0), _inwList{}.REGISTER varchar(6), _inwList{}.sector varchar(5), _inwList{}.stadsdeel varchar(16), _inwList{}.wijknaam varchar(30), _inwList{}.gemeensch varchar(12), _inwList{}.BevRegID varchar(10), _inwList{}.CRAB_merge varchar(254), _inwList{}.CRABadrID varchar(10), _inwList{}.GEMNM varchar(4), _inwList{}.PKANCODE number(11,0), EigWoning varchar(30), InwEigenaars number(4,0), _inwEigenaarsList{}.officialId varchar(12), _inwEigenaarsList{}.name varchar(80), _inwEigenaarsList{}.firstname varchar(12), _inwEigenaarsList{}.birthdate varchar(11), _inwEigenaarsList{}.country varchar(3), _inwEigenaarsList{}.zipCode varchar(4), _inwEigenaarsList{}.municipality_fr varchar(30),
      _inwEigenaarsList{}.municipality_nl varchar(30), _inwEigenaarsList{}.street_fr varchar(30), _inwEigenaarsList{}.street_nl varchar(30), _inwEigenaarsList{}.number varchar(5), _inwEigenaarsList{}.boxNumber varchar(5), _inwEigenaarsList{}.officialId_partner varchar(13), _inwEigenaarsList{}.name_partner varchar(23), _inwEigenaarsList{}.firstName_partner varchar(13), _inwEigenaarsList{}.birthdate_partner varchar(11), _inwEigenaarsList{}.country_partner varchar(3), _inwEigenaarsList{}.zipCode_partner varchar(5), _inwEigenaarsList{}.municipality_partner_fr varchar(30), _inwEigenaarsList{}.municipality_partner_nl varchar(30), _inwEigenaarsList{}.street_partner_fr varchar(30), _inwEigenaarsList{}.street_partner_nl varchar(30), _inwEigenaarsList{}.number_partner varchar(20), _inwEigenaarsList{}.boxNumber_partner varchar(5), _inwEigenaarsList{}.coOwner varchar(16), _inwEigenaarsList{}.anonymousOwner varchar(1), _inwEigenaarsList{}.CRABadrID varchar(10), _inwOwnerList{}.propertySituationIdf varchar(9), _inwOwnerList{}.order varchar(3), _inwOwnerList{}.partyType varchar(3), _inwOwnerList{}.right varchar(51), _inwOwnerList{}.right_trad varchar(51), _inwOwnerList{}.managedBy number(2,0), _inwOwnerList{}.officialId varchar(12), _inwOwnerList{}.name varchar(80), _inwOwnerList{}.firstname varchar(12), _inwOwnerList{}.birthdate varchar(11),
      _inwOwnerList{}.country varchar(3), _inwOwnerList{}.zipCode varchar(4), _inwOwnerList{}.municipality_fr varchar(30), _inwOwnerList{}.municipality_nl varchar(30), _inwOwnerList{}.street_fr varchar(30), _inwOwnerList{}.street_nl varchar(30), _inwOwnerList{}.number varchar(5), _inwOwnerList{}.boxNumber varchar(5), _inwOwnerList{}.officialId_partner varchar(13), _inwOwnerList{}.name_partner varchar(23), _inwOwnerList{}.firstName_partner varchar(13), _inwOwnerList{}.birthdate_partner varchar(11), _inwOwnerList{}.country_partner varchar(3), _inwOwnerList{}.zipCode_partner varchar(5), _inwOwnerList{}.municipality_partner_fr varchar(30), _inwOwnerList{}.municipality_partner_nl varchar(30), _inwOwnerList{}.street_partner_fr varchar(30), _inwOwnerList{}.street_partner_nl varchar(30), _inwOwnerList{}.number_partner varchar(20), _inwOwnerList{}.boxNumber_partner varchar(5), _inwOwnerList{}.anonymousOwner varchar(1), _inwOwnerList{}.coOwner varchar(16), _inwOwnerList{}.dateSituation varchar(9), _inwOwnerList{}.CRABadrID varchar(10), _inwParcelList{}.constructionIndication number(4,0), _inwParcelList{}.propertySituationIdf number(8,0), _inwParcelList{}.divCad number(5,0), _inwParcelList{}.section varchar(1), _inwParcelList{}.primaryNumber number(3,0), _inwParcelList{}.bisNumber number(2,0),
      _inwParcelList{}.exponentLetter varchar(1), _inwParcelList{}.exponentNumber number(3,0), _inwParcelList{}.partNumber varchar(5), _inwParcelList{}.capakey varchar(17), _inwParcelList{}.order varchar(4), _inwParcelList{}.nature varchar(3), _inwParcelList{}.descriptPrivate varchar(35), _inwParcelList{}.block varchar(2), _inwParcelList{}.floor varchar(2), _inwParcelList{}.floorSituation varchar(5), _inwParcelList{}.crossDetail varchar(20), _inwParcelList{}.matUtil varchar(1), _inwParcelList{}.notTaxedMatUtil varchar(3), _inwParcelList{}.nisCom varchar(6), _inwParcelList{}.street_situation varchar(20), _inwParcelList{}.street_translation varchar(1), _inwParcelList{}.street_code varchar(6), _inwParcelList{}.number varchar(6), _inwParcelList{}.polWa varchar(8), _inwParcelList{}.surfaceNotTaxable number(10,0), _inwParcelList{}.surfaceTaxable number(10,0), _inwParcelList{}.surfaceVerif varchar(2), _inwParcelList{}.constructionYear number(5,0), _inwParcelList{}.soilIndex number(2,0), _inwParcelList{}.soilRent varchar(2), _inwParcelList{}.cadastralIncomePerSurface number(3,0), _inwParcelList{}.cadastralIncomePerSurfaceOtherDi number(2,0), _inwParcelList{}.numberCadastralIncome number(1,0), _inwParcelList{}.charCadastralIncome varchar(1), _inwParcelList{}.cadastralIncome number(6,0),
      _inwParcelList{}.dateEndExoneration varchar(1), _inwParcelList{}.decrete varchar(1), _inwParcelList{}.constructionType varchar(2), _inwParcelList{}.floorNumberAboveground number(2,0), _inwParcelList{}.garret number(2,0), _inwParcelList{}.physModYear number(5,0), _inwParcelList{}.constructionQuality varchar(2), _inwParcelList{}.garageNumber number(2,0), _inwParcelList{}.centralHeating number(2,0), _inwParcelList{}.bathroomNumber number(2,0), _inwParcelList{}.housingUnitNumber number(2,0), _inwParcelList{}.placeNumber number(3,0), _inwParcelList{}.builtSurface number(5,0), _inwParcelList{}.usedSurface number(4,0), _inwParcelList{}.dateSituation varchar(9), _inwParcelList{}.aard varchar(10), _inwParcelList{}.bouwjaar varchar(25), _inwParcelList{}.GebouwType varchar(200)
AttributeRenamer_4
    ATTR_TABLE = RENAME_SET_DEFAULT InwEigenaars > InwEigenaa
    -> BEW_Gebouweenheden_Adressen (writer ESRISHAPE_1)
BEW_Gebouweenheden_Adressen (writer ESRISHAPE_1)
    attributes: TypeEenh char(60), Functie char(60), Domicilie char(60), CRABadrID char(10), capakey char(17), ParticHh number(3,0), EenprsHh number(3,0), MeerprsHh number(3,0), GemeensHh number(3,0), HandelID char(10), STRAATNM char(254), HUISNR char(10), SUBADRES char(254), PKANCODE number(11,0), GEMNM char(4), GebouwType char(150), EigWoning char(30), InwEigenaa number(4,0)
004_KAD_percelen (reader FFS_5)
    attributes: Gebouweenh number(3,0), Wooneenh number(3,0), constructionIndication varchar(254), capakey varchar(17), nature varchar(254), descriptPrivate varchar(254), constructionType varchar(254), housingUnitNumber number(3,0), _kadparcelList{}.constructionIndication number(4,0), _kadparcelList{}.propertySituationIdf number(8,0), _kadparcelList{}.divCad number(5,0), _kadparcelList{}.section varchar(1), _kadparcelList{}.primaryNumber number(3,0), _kadparcelList{}.bisNumber number(2,0), _kadparcelList{}.exponentLetter varchar(1), _kadparcelList{}.exponentNumber number(3,0), _kadparcelList{}.partNumber varchar(5), _kadparcelList{}.capakey varchar(17), _kadparcelList{}.order varchar(4), _kadparcelList{}.nature varchar(3), _kadparcelList{}.descriptPrivate varchar(35), _kadparcelList{}.block varchar(2), _kadparcelList{}.floor varchar(2), _kadparcelList{}.floorSituation varchar(5), _kadparcelList{}.crossDetail varchar(20), _kadparcelList{}.matUtil varchar(1), _kadparcelList{}.notTaxedMatUtil varchar(3), _kadparcelList{}.nisCom varchar(6), _kadparcelList{}.street_situation varchar(20), _kadparcelList{}.street_translation varchar(1),
      _kadparcelList{}.street_code varchar(6), _kadparcelList{}.number varchar(6), _kadparcelList{}.polWa varchar(8), _kadparcelList{}.surfaceNotTaxable number(10,0), _kadparcelList{}.surfaceTaxable number(10,0), _kadparcelList{}.surfaceVerif varchar(2), _kadparcelList{}.constructionYear number(5,0), _kadparcelList{}.soilIndex number(2,0), _kadparcelList{}.soilRent varchar(2), _kadparcelList{}.cadastralIncomePerSurface number(3,0), _kadparcelList{}.cadastralIncomePerSurfaceOtherDi number(2,0), _kadparcelList{}.numberCadastralIncome number(1,0), _kadparcelList{}.charCadastralIncome varchar(1), _kadparcelList{}.cadastralIncome number(6,0), _kadparcelList{}.dateEndExoneration varchar(1), _kadparcelList{}.decrete varchar(1), _kadparcelList{}.constructionType varchar(2), _kadparcelList{}.floorNumberAboveground number(2,0), _kadparcelList{}.garret number(2,0), _kadparcelList{}.physModYear number(5,0), _kadparcelList{}.constructionQuality varchar(2), _kadparcelList{}.garageNumber number(2,0), _kadparcelList{}.centralHeating number(2,0), _kadparcelList{}.bathroomNumber number(2,0), _kadparcelList{}.housingUnitNumber number(2,0), _kadparcelList{}.placeNumber number(3,0), _kadparcelList{}.builtSurface number(5,0), _kadparcelList{}.usedSurface number(4,0), _kadparcelList{}.dateSituation varchar(9), _kadparcelList{}.aard varchar(10),
      _kadparcelList{}.bouwjaar varchar(25), _kadparcelList{}.GebouwType varchar(200), ParticHh number(3,0), EenprsHh number(3,0), MeerprsHh number(3,0), GemeensHh number(3,0), GebouwType varchar(150), _gebouweenhList{}.TypeEenh varchar(60), _gebouweenhList{}.Functie varchar(60), _gebouweenhList{}.HandelID varchar(10), _gebouweenhList{}.Domicilie varchar(60), _gebouweenhList{}.CRABadrID varchar(10), _gebouweenhList{}.ParticHh number(3,0), _gebouweenhList{}.EenprsHh number(3,0), _gebouweenhList{}.MeerprsHh number(3,0), _gebouweenhList{}.GemeensHh number(3,0), _gebouweenhList{}.STRAATNM varchar(254), _gebouweenhList{}.HUISNR varchar(10), _gebouweenhList{}.SUBADRES varchar(5), _gebouweenhList{}.PKANCODE number(11,0), _gebouweenhList{}.GEMNM varchar(4), _gebouweenhList{}.GebouwType varchar(150), _gebouweenhList{}.EigWoning varchar(30), _gebouweenhList{}.InwEigenaars number(4,0)
    -> ListRenamer
ListRenamer
    LIST_COMPONENT_NAMES = _kadparcelList{},_kadParcelList{}
    LIST_NAME = _kadparcelList{}
    LIST_ACTION = Rename
    LEAVE_ORIG = No
    -> BEW_Percelen (writer FFS_12)
    -> BEW_Percelen (writer ESRISHAPE_1)
BEW_Percelen (writer FFS_12)
    attributes: capakey varchar(17), Gebouweenh number(3,0), Wooneenh number(3,0), GebouwType varchar(150), ParticHh number(3,0), EenprsHh number(3,0), MeerprsHh number(3,0), GemeensHh number(3,0), _kadParcelList{}.constructionIndication number(4,0), _kadParcelList{}.propertySituationIdf number(8,0), _kadParcelList{}.divCad number(5,0), _kadParcelList{}.section varchar(1), _kadParcelList{}.primaryNumber number(3,0), _kadParcelList{}.bisNumber number(2,0), _kadParcelList{}.exponentLetter varchar(1), _kadParcelList{}.exponentNumber number(3,0), _kadParcelList{}.partNumber varchar(5), _kadParcelList{}.capakey varchar(17), _kadParcelList{}.order varchar(4), _kadParcelList{}.nature varchar(3), _kadParcelList{}.descriptPrivate varchar(35), _kadParcelList{}.block varchar(2), _kadParcelList{}.floor varchar(2), _kadParcelList{}.floorSituation varchar(5), _kadParcelList{}.crossDetail varchar(20), _kadParcelList{}.matUtil varchar(1), _kadParcelList{}.notTaxedMatUtil varchar(3), _kadParcelList{}.nisCom varchar(6), _kadParcelList{}.street_situation varchar(20), _kadParcelList{}.street_translation varchar(1),
      _kadParcelList{}.street_code varchar(6), _kadParcelList{}.number varchar(6), _kadParcelList{}.polWa varchar(8), _kadParcelList{}.surfaceNotTaxable number(10,0), _kadParcelList{}.surfaceTaxable number(10,0), _kadParcelList{}.surfaceVerif varchar(2), _kadParcelList{}.constructionYear number(5,0), _kadParcelList{}.soilIndex number(2,0), _kadParcelList{}.soilRent varchar(2), _kadParcelList{}.cadastralIncomePerSurface number(3,0), _kadParcelList{}.cadastralIncomePerSurfaceOtherDi number(2,0), _kadParcelList{}.numberCadastralIncome number(1,0), _kadParcelList{}.charCadastralIncome varchar(1), _kadParcelList{}.cadastralIncome number(6,0), _kadParcelList{}.dateEndExoneration varchar(1), _kadParcelList{}.decrete varchar(1), _kadParcelList{}.constructionType varchar(2), _kadParcelList{}.floorNumberAboveground number(2,0), _kadParcelList{}.garret number(2,0), _kadParcelList{}.physModYear number(5,0), _kadParcelList{}.constructionQuality varchar(2), _kadParcelList{}.garageNumber number(2,0), _kadParcelList{}.centralHeating number(2,0), _kadParcelList{}.bathroomNumber number(2,0), _kadParcelList{}.housingUnitNumber number(2,0), _kadParcelList{}.placeNumber number(3,0), _kadParcelList{}.builtSurface number(5,0), _kadParcelList{}.usedSurface number(4,0), _kadParcelList{}.dateSituation varchar(9), _kadParcelList{}.aard varchar(10),
      _kadParcelList{}.bouwjaar varchar(25), _kadParcelList{}.GebouwType varchar(200), _gebouweenhList{}.TypeEenh varchar(60), _gebouweenhList{}.Functie varchar(60), _gebouweenhList{}.HandelID varchar(10), _gebouweenhList{}.Domicilie varchar(60), _gebouweenhList{}.CRABadrID varchar(10), _gebouweenhList{}.ParticHh number(3,0), _gebouweenhList{}.EenprsHh number(3,0), _gebouweenhList{}.MeerprsHh number(3,0), _gebouweenhList{}.GemeensHh number(3,0), _gebouweenhList{}.STRAATNM varchar(254), _gebouweenhList{}.HUISNR varchar(10), _gebouweenhList{}.SUBADRES varchar(5), _gebouweenhList{}.PKANCODE number(11,0), _gebouweenhList{}.GEMNM varchar(4), _gebouweenhList{}.GebouwType varchar(150), _gebouweenhList{}.EigWoning varchar(30), _gebouweenhList{}.InwEigenaars number(4,0)
BEW_Percelen (writer ESRISHAPE_1)
    attributes: capakey char(17), Gebouweenh number(3,0), Wooneenh number(3,0), GebouwType char(150), ParticHh number(3,0), EenprsHh number(3,0), MeerprsHh number(17,0), GemeensHh number(3,0)
000_KAD_parcel (reader FFS_6)
    attributes: propertySituationIdf number(8,0), divCad number(5,0), section varchar(1), primaryNumber number(4,0), bisNumber number(2,0), exponentLetter varchar(1), exponentNumber number(3,0), partNumber varchar(5), capakey varchar(17), order varchar(4), nature varchar(3), descriptPrivate varchar(35), block varchar(2), floor varchar(2), floorSituation varchar(5), crossDetail varchar(20), matUtil varchar(1), notTaxedMatUtil varchar(3), nisCom varchar(6), street_situation varchar(20), street_translation varchar(1), street_code varchar(6), number varchar(6), polWa varchar(8), surfaceNotTaxable number(10,0), surfaceTaxable number(10,0), surfaceVerif varchar(2), constructionYear number(5,0), soilIndex number(2,0), soilRent varchar(2),
      cadastralIncomePerSurface number(3,0), cadastralIncomePerSurfaceOtherDi number(2,0), numberCadastralIncome number(1,0), charCadastralIncome varchar(1), cadastralIncome number(8,0), dateEndExoneration varchar(1), decrete varchar(1), constructionIndication number(4,0), constructionType varchar(2), floorNumberAboveground number(2,0), garret number(2,0), physModYear number(5,0), constructionQuality varchar(2), garageNumber number(3,0), centralHeating number(3,0), bathroomNumber number(3,0), housingUnitNumber number(2,0), placeNumber number(4,0), builtSurface number(5,0), usedSurface number(5,0), dateSituation varchar(9), aard varchar(10), bouwjaar varchar(25)
    -> AttributeManager
    -> BEW_Eigendommen (writer FFS_13)
BEW_Eigendommen (writer FFS_13)
    attributes: propertySituationIdf number(8,0), divCad number(5,0), section varchar(1), primaryNumber number(4,0), bisNumber number(2,0), exponentLetter varchar(1), exponentNumber number(3,0), partNumber varchar(5), capakey varchar(17), order varchar(4), nature varchar(3), descriptPrivate varchar(35), block varchar(2), floor varchar(2), floorSituation varchar(5), crossDetail varchar(20), matUtil varchar(1), notTaxedMatUtil varchar(3), nisCom varchar(6), street_situation varchar(20), street_translation varchar(1), street_code varchar(6), number varchar(6), polWa varchar(8), surfaceNotTaxable number(10,0), surfaceTaxable number(10,0), surfaceVerif varchar(2), constructionYear number(5,0), soilIndex number(2,0), soilRent varchar(2),
      cadastralIncomePerSurface number(3,0), cadastralIncomePerSurfaceOtherDi number(2,0), numberCadastralIncome number(1,0), charCadastralIncome varchar(1), cadastralIncome number(8,0), dateEndExoneration varchar(1), decrete varchar(1), constructionIndication number(4,0), constructionType varchar(2), floorNumberAboveground number(2,0), garret number(2,0), physModYear number(5,0), constructionQuality varchar(2), garageNumber number(3,0), centralHeating number(3,0), bathroomNumber number(3,0), housingUnitNumber number(2,0), placeNumber number(4,0), builtSurface number(5,0), usedSurface number(5,0), dateSituation varchar(9), aard varchar(10), bouwjaar varchar(25)
AttributeManager
    ATTR_TABLE:
      RENAME_SET_VALUE propertySituationIdf > propSitIdf
      RENAME_SET_VALUE primaryNumber > primNumber
      RENAME_SET_VALUE exponentLetter > expLetter
      RENAME_SET_VALUE exponentNumber > expNumber
      RENAME_SET_VALUE descriptPrivate > descrPriv
      RENAME_SET_VALUE floorSituation > floorSitua
      RENAME_SET_VALUE crossDetail > crossDetai
      RENAME_SET_VALUE notTaxedMatUtil > notTaxedMa
      RENAME_SET_VALUE street_situation > street_sit
      RENAME_SET_VALUE street_translation > street_tra
      RENAME_SET_VALUE surfaceNotTaxable > surfNotTax
      RENAME_SET_VALUE surfaceTaxable > surfTax
      RENAME_SET_VALUE surfaceVerif > surfVerif
      RENAME_SET_VALUE constructionYear > constrYear
      RENAME_SET_VALUE cadastralIncomePerSurface > cadIPrSf
      RENAME_SET_VALUE cadastralIncomePerSurfaceOtherDi > cadIPrSfOD
      RENAME_SET_VALUE numberCadastralIncome > numberCadI
      RENAME_SET_VALUE charCadastralIncome > charCadI
      RENAME_SET_VALUE cadastralIncome > cadIncome
      RENAME_SET_VALUE dateEndExoneration > dateEndExo
      RENAME_SET_VALUE constructionIndication > constrInd
      RENAME_SET_VALUE constructionType > constrType
      RENAME_SET_VALUE floorNumberAboveground > floorNumbe
      RENAME_SET_VALUE physModYear > physModYea
      RENAME_SET_VALUE constructionQuality > constrQual
      RENAME_SET_VALUE garageNumber > garageNumb
      RENAME_SET_VALUE centralHeating > centralHea
      RENAME_SET_VALUE bathroomNumber > bathroomNb
      RENAME_SET_VALUE housingUnitNumber > housingUni
      RENAME_SET_VALUE placeNumber > placeNumbe
      RENAME_SET_VALUE builtSurface > builtSurf
      RENAME_SET_VALUE usedSurface > usedSurf
      RENAME_SET_VALUE street_code > street_cod
      RENAME_SET_VALUE dateSituation > dateSit
    -> BEW_Eigendommen (writer ESRISHAPE_1)
BEW_Eigendommen (writer ESRISHAPE_1)
    attributes: propSitIdf number(8,0), divCad number(5,0), section char(1), primNumber number(4,0), bisNumber number(2,0), expLetter char(1), expNumber number(3,0), partNumber char(5), capakey char(17), order char(4), nature char(3), descrPriv char(35), block char(2), floor char(2), floorSitua char(5), crossDetai char(20), matUtil char(1), notTaxedMa char(3), nisCom char(6), street_sit char(20), street_tra char(1), street_cod char(6), number char(6), polWa char(8), surfNotTax number(10,0), surfTax number(10,0), surfVerif char(2), constrYear number(5,0), soilIndex number(2,0), soilRent char(2),
      cadIPrSf number(3,0), cadIPrSfOD number(2,0), numberCadI number(1,0), charCadI char(1), cadIncome number(8,0), dateEndExo char(1), decrete char(1), constrInd number(4,0), constrType char(4), floorNumbe number(4,0), garret number(4,0), physModYea number(5,0), constrQual char(2), garageNumb number(3,0), centralHea number(3,0), bathroomNb number(3,0), housingUni number(4,0), placeNumbe number(4,0), builtSurf number(5,0), usedSurf number(5,0), dateSit char(9), aard char(10), bouwjaar char(25)
004_KAD_owner (reader FFS_7)
    attributes: propertySituationIdf varchar(9), order varchar(3), partyType varchar(3), right varchar(51), right_trad varchar(51), managedBy number(2,0), officialId varchar(12), name varchar(80), firstname varchar(12), birthdate varchar(11), country varchar(3), zipCode varchar(4), municipality_fr varchar(30), municipality_nl varchar(30), street_fr varchar(30), street_nl varchar(30), number varchar(5), boxNumber varchar(5), officialId_partner varchar(13), name_partner varchar(23), firstName_partner varchar(13), birthdate_partner varchar(11), country_partner varchar(3), zipCode_partner varchar(5), municipality_partner_fr varchar(30), municipality_partner_nl varchar(30), street_partner_fr varchar(30), street_partner_nl varchar(30), number_partner varchar(20), boxNumber_partner varchar(5),
      coOwner varchar(16), anonymousOwner varchar(1), dateSituation varchar(9), CRABadrID varchar(10)
    -> BEW_Eigenaars (writer FFS_14)
    -> AttributeManager_2
BEW_Eigenaars (writer FFS_14)
    attributes: propertySituationIdf varchar(9), order varchar(3), partyType varchar(3), right varchar(51), right_trad varchar(51), managedBy number(2,0), officialId varchar(12), name varchar(80), firstname varchar(12), birthdate varchar(11), country varchar(3), zipCode varchar(4), municipality_fr varchar(30), municipality_nl varchar(30), street_fr varchar(30), street_nl varchar(30), number varchar(5), boxNumber varchar(5), officialId_partner varchar(13), name_partner varchar(23), firstName_partner varchar(13), birthdate_partner varchar(11), country_partner varchar(3), zipCode_partner varchar(5), municipality_partner_fr varchar(30), municipality_partner_nl varchar(30), street_partner_fr varchar(30), street_partner_nl varchar(30), number_partner varchar(20), boxNumber_partner varchar(5),
      coOwner varchar(16), anonymousOwner varchar(1), dateSituation varchar(9), CRABadrID varchar(10)
AttributeManager_2
    ATTR_TABLE:
      RENAME_SET_VALUE propertySituationIdf > propSitIdf
      RENAME_SET_VALUE officialId_partner > par_offici
      RENAME_SET_VALUE name_partner > par_name
      RENAME_SET_VALUE firstName_partner > par_firstN
      RENAME_SET_VALUE birthdate_partner > par_birthd
      RENAME_SET_VALUE country_partner > par_countr
      RENAME_SET_VALUE zipCode_partner > par_zipCod
      RENAME_SET_VALUE number_partner > par_number
      RENAME_SET_VALUE boxNumber_partner > par_boxNum
      RENAME_SET_VALUE anonymousOwner > anonymousO
      RENAME_SET_VALUE municipality_fr > munic_fr
      RENAME_SET_VALUE municipality_nl > munic_nl
      RENAME_SET_VALUE municipality_partner_fr > par_mun_fr
      RENAME_SET_VALUE municipality_partner_nl > par_mun_nl
      RENAME_SET_VALUE street_partner_fr > par_str_fr
      RENAME_SET_VALUE street_partner_nl > par_str_nl
      RENAME_SET_VALUE dateSituation > dateSit
    -> BEW_Eigenaars (writer ESRISHAPE_1)
BEW_Eigenaars (writer ESRISHAPE_1)
    attributes: propSitIdf char(9), order char(3), partyType char(3), right char(51), right_trad char(51), managedBy number(2,0), officialId char(12), name char(80), firstname char(12), birthdate char(11), country char(3), zipCode char(4), munic_fr char(30), munic_nl char(30), street_fr char(30), street_nl char(30), number char(5), boxNumber char(5), par_offici char(13), par_name char(23), par_firstN char(13), par_birthd char(11), par_countr char(3), par_zipCod char(5), par_mun_fr char(30), par_mun_nl char(30), par_str_fr char(30), par_str_nl char(30), par_number char(20), par_boxNum char(5),
      coOwner char(16), anonymousO char(1), dateSit char(9), CRABadrID char(10)
BEW_Inwoners: Inspector
BEW_Huishoudens: Inspector
004_Gebouweenheden_Adressen: Inspector
004_KAD_percelen: Inspector
BEW_Adressen: Inspector
