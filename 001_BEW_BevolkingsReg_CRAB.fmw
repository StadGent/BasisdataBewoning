FME workspace 001_BEW_BevolkingsReg_CRAB.fmw
Title: 001_BEW_BevolkingsReg_CRAB.fmw
Description: Bewerkingen: 
Koppeling Bevolkingsregister aan adreslocaties uit CRAB.
History: 2016-10-06,Jonas Verstraete,Initial version

Parameters:
- DestDataset_SHAPE = ..\data\intermediate\001   # Destination Esri Shape Folder
- DestDataset_CSV = ..\data\intermediate\001   # Destination CSV (CommaSeparatedValue) Folder
- SourceDataset_FFS = ..\data\intermediate\000\000_CRAB_alladr.ffs   # Source FME Feature Store (FFS) File(s)
- SourceDataset_FFS_4 = ..\data\intermediate\000\000_BevReg.ffs   # Source FME Feature Store (FFS) File(s)
- DestDataset_FFS = ..\data\intermediate\001\001_BevReg_CRAB.ffs   # Destination FME Feature Store (FFS) File
- DestDataset_FFS_2 = ..\data\intermediate\001\001_BevReg_adr_notCRAB.ffs   # Destination FME Feature Store (FFS) File
- MINX =   # Minimum X
- MINY =   # Minimum Y
- MAXX =   # Maximum X
- MAXY =   # Maximum Y
- GeolocatorRequestURL =   # " " Attribute Value

Readers:
- FFS_1: FFS from $(SourceDataset_FFS)
- FFS_2: FFS from $(SourceDataset_FFS_4)

Writers:
- SHAPE_1: SHAPE to $(DestDataset_SHAPE)
- CSV_1: CSV to $(DestDataset_CSV)
- FFS_3: FFS to $(DestDataset_FFS) in EPSG:31370
- FFS_4: FFS to $(DestDataset_FFS_2)

Note: 001_BEW_BevolkingsReg_CRAB.fmw / Bewerkingen: / Koppeling Bevolkingsregister aan adreslocaties uit CRAB.
000_BevReg (reader FFS_2)
    attributes: POSTKODE varchar(4), STRAATKODE varchar(8), NUMMER varchar(5), INDEX varchar(5), GEBDAT varchar(11), GESLACHT varchar(2), NATIONALITEIT number(4,0), VERWERVING number(3,0), REFPERS varchar(2), GEZINSGROOTTE number(3,0), AANTKIND number(3,0), BURGSTAAT varchar(15), NAT_OUD number(4,0), REGISTER varchar(6), sector varchar(5), stadsdeel varchar(16), wijknaam varchar(30), gemeensch varchar(12), BevRegID varchar(10), CRAB_StraatId varchar(5), CRAB_SubkantonCode varchar(4), CRAB_Straatnaam char(100), CRAB_NISGemeente char(5), CRAB_Gemeente char(50)
    -> TestFilter
TestFilter
    DEFAULT_VALUE = <UNFILTERED>
    TEST_LIST = BOOL_OP,OR,COMPOSITE_TEST,<Unused>,TEST_CLAUSE,"TEST CRAB_StraatId NOT_ATTRIBUTE_IS_MISSING """"",CRAB_StraatId NOT_ATTRIBUTE_IS_MISSING
    CRAB_StraatId NOT_ATTRIBUTE_IS_MISSING -> StringSearcher
    <UNFILTERED> -> VertexCreator
StringSearcher
    MATCHED_RESULT_ATTR = _matched_characters
    MATCHED_PARTS_ATTR = _matched_parts
    REGEXP = ^[0-9]+$
    CASE = no
    STRING_TO_SEARCH = @Value(INDEX)
    MATCHED -> AttributeCreator
    NOT_MATCHED -> StringSearcher_2
AttributeCreator
    ATTR_LIST = SUBADR,@Value(INDEX),HUISNR,@TrimLeft(@Value(NUMMER),0)
    -> AttributeRemover_5
StringSearcher_2
    MATCHED_RESULT_ATTR = _matched_characters
    MATCHED_PARTS_ATTR = _matched_parts
    REGEXP = ([a-z]|[A-Z])(.*)
    CASE = no
    STRING_TO_SEARCH = @Value(INDEX)
    MATCHED -> AttributeCreator_2
    NOT_MATCHED -> AttributeCreator_13
AttributeCreator_2
    ATTR_LIST = HUISNR,@TrimLeft(@Value(NUMMER),0)@Value(_matched_parts{0}),SUBADR,"FME_CONDITIONAL:DEFAULT_VALUE'_FME_NO_OP_'BOOL_OP;OR;COMPOSITE_TEST;<Unused>;TEST @Value(_matched_parts{1}) > 0'@PadLeft(@Value(_matched_parts{1}),4,0)'FME_NUM_CONDITIONS2___"
    -> AttributeRemover_5
AttributeCreator_13
    ATTR_LIST = HUISNR,@TrimLeft(@Value(NUMMER),0)
    -> AttributeRemover_5
Note: Referenced: / Foute CRAB StraatID in CRAB_alladr (db RuimtelijkLoket) of list RR_Straatnamen (download CRAB.ws)
AttributeRemover_5
    REMOVE_ATTRS = _matched_characters
    LIST_ATTRS = _matched_parts{}
    -> FeatureMerger [REQUESTOR]
000_CRAB_alladr (reader FFS_1)
    attributes: CRABadrID varchar(10), STRAATNMID number(11,0), STRAATNM varchar(255), HUISNRID number(11,0), HUISNR varchar(10), HUISNR_BEG varchar(20), HUISNR_TIJ varchar(20), HUISNR_EIN varchar(20), SUBADRESID number(11,0), SUBADRES varchar(255), SUBADR_BEG varchar(20), AARDSUBADR number(11,0), NISGEMCODE varchar(5), PKANCODE number(11,0), GEMNM varchar(4), AARDADRPOS number(11,0), X number(31,15), Y number(31,15), SUBADR_TIJ varchar(20), SUBADR_EIN varchar(20)
    -> PassThrough_3
Note: Extra adressen obv KAD / * KAD adres dat enkel op hoofdadres (STRAAT en HUISNR) met CRAB gematched / >> als afzonderlijk adres beschouwd (verschillend SUBNUMMER) - HFD00000 zodat / * KAD adres dat eerst door geolocator (match>90) en nadien gematched op STRAAT en HUISNR / >> KAD adressen zijn gecorrigeerd. bvb 5A > 5, ...: als afzonderlijk adres beschouwd - COR00000 / *Adres dat na geocoderen niet meer kan gemerged aan CRAB-adres / (No clean data: adres BevReg niet in GRAB, wel in CRAB geolocator? Te onderzoeken) / >> Nieuwe CRAB_adrID aangemaakt (GL0000)
PassThrough_3: Tester
    TEST_CLAUSE = TEST 1 = 1
    BOOL_OP = OR
    TEST_DESCRIPTION = ""
    TEST_MODE = Automatic
    PASSED -> FeatureMerger_2 [SUPPLIER]
    PASSED -> FeatureMerger [SUPPLIER]
    PASSED -> Sorter_2
Note: Merge on CRAB_StraatId, HUISNR and SUBADR
FeatureMerger
    IGNORE_NULLS = No
    MERGE_TYPE = Attributes and Geometry
    ATTR_ACCUM_MODE = Merge Supplier
    ATTR_CONFLICT_RES = Use Requestor
    SUPPLIERS_FIRST = No
    JOIN_KEYS = @Value(CRAB_StraatId) @Value(STRAATNMID) AUTO @Value(HUISNR) @Value(HUISNR) AUTO @Value(SUBADR) @Value(SUBADRES) AUTO
    PROCESS_DUPS = No
    MERGED -> AttributeCreator_3
    NOT_MERGED -> FeatureMerger_2 [REQUESTOR]
Note: Merge on STRAATNM,HUISNR and SUBADR
FeatureMerger_2
    IGNORE_NULLS = No
    MERGE_TYPE = Attributes and Geometry
    ATTR_ACCUM_MODE = Merge Supplier
    ATTR_CONFLICT_RES = Use Requestor
    SUPPLIERS_FIRST = No
    JOIN_KEYS = @Value(CRAB_Straatnaam) @Value(STRAATNM) AUTO @Value(HUISNR) @Value(HUISNR) AUTO @Value(SUBADR) @Value(SUBADRES) AUTO
    PROCESS_DUPS = No
    MERGED -> AttributeCreator_3
    NOT_MERGED -> Sorter
Sorter
    SORT_PARM = HUISNR ALPHA ASCENDING SUBADR NUMERIC ASCENDING
    SORTED -> FeatureMerger_4 [REQUESTOR]
Note: Resterende NotMerged: Subadres kan verschillen! / Koppeling verder gebruiiken? / Eerst sorteren zodat voor beiden eerste subadres gebruikt. / Dit moet als apart adres/wooneenheid worden beschouwd
Note: Referenced: / Foute CRAB StraatID in CRAB_alladr (db RuimtelijkLoket) of list RR_Straatnamen (download CRAB.ws)
Sorter_2
    SORT_PARM = HUISNR ALPHA ASCENDING SUBADRES NUMERIC ASCENDING
    SORTED -> FeatureMerger_4 [SUPPLIER]
    SORTED -> FeatureMerger_5 [SUPPLIER]
    SORTED -> FeatureMerger_3 [SUPPLIER]
Note: Merge on CRAB_StraatId and HUISNR
FeatureMerger_4
    IGNORE_NULLS = No
    MERGE_TYPE = Attributes and Geometry
    ATTR_ACCUM_MODE = Merge Supplier
    ATTR_CONFLICT_RES = Use Supplier
    SUPPLIERS_FIRST = No
    JOIN_KEYS = @Value(CRAB_StraatId) @Value(STRAATNMID) AUTO @Value(HUISNR) @Value(HUISNR) AUTO
    PROCESS_DUPS = No
    MERGED -> AttributeCreator_10
    NOT_MERGED -> FeatureMerger_5 [REQUESTOR]
Note: Merge on STRAATNM and HUISNR
FeatureMerger_5
    IGNORE_NULLS = No
    MERGE_TYPE = Attributes and Geometry
    ATTR_ACCUM_MODE = Merge Supplier
    ATTR_CONFLICT_RES = Use Supplier
    SUPPLIERS_FIRST = No
    JOIN_KEYS = @Value(CRAB_Straatnaam) @Value(STRAATNM) AUTO @Value(HUISNR) @Value(HUISNR) AUTO
    PROCESS_DUPS = No
    MERGED -> AttributeCreator_10
    NOT_MERGED -> TestFilter_2
AttributeCreator_10
    ATTR_TABLE = SET_TO CRABadrID = HFD@Value(CRABadrID)
    -> AttributeCreator_6
TestFilter_2
    DEFAULT_VALUE = <UNFILTERED>
    TEST_LIST = BOOL_OP,OR,COMPOSITE_TEST,<Unused>,TEST_CLAUSE,"TEST $(GeolocatorRequestURL) NOT_ATTRIBUTE_HAS_VALUE """"",NoGeolocator
    NoGeolocator -> VertexCreator
    <UNFILTERED> -> AttributeCreator_9
Note: X,Y ingevuld?
Tester_3
    TEST_CLAUSE:
      TEST GL_X NOT_ATTRIBUTE_VALUE_NULL ""
      TEST GL_X NOT_ATTRIBUTE_IS_EMPTY ""
      TEST GL_X NOT_ATTRIBUTE_IS_MISSING ""
      TEST @Value(GL_Match) >= 95
    BOOL_OP = AND
    TEST_DESCRIPTION = ""
    TEST_MODE = Automatic
    PASSED -> FeatureMerger_3 [REQUESTOR]
    FAILED -> VertexCreator
Note: Merge on geolocator STRAATNM and HUISNR
FeatureMerger_3
    IGNORE_NULLS = No
    MERGE_TYPE = Attributes and Geometry
    ATTR_ACCUM_MODE = Merge Supplier
    ATTR_CONFLICT_RES = Use Supplier
    SUPPLIERS_FIRST = No
    JOIN_KEYS = @Value(GL_Straatnm) @Value(STRAATNM) AUTO @Value(GL_Huisnr) @Value(HUISNR) AUTO
    PROCESS_DUPS = No
    MERGED -> AttributeCreator_11
    NOT_MERGED -> Aggregator
Note: Adres corrected by geolocator / subadres kan verschillen, letter kan verschillen / ...
AttributeCreator_11
    ATTR_TABLE = SET_TO CRABadrID = COR@Value(CRABadrID)
    -> AttributeCreator_7
Aggregator
    GROUP_BY = NUMMER STRAATKODE INDEX
    LIST_NAME = _InwListperBevRegadr
    ORDERED = No
    SEP = ,
    ACCUM_ATTRS_NAME = Yes
    AGGREGATE_TYPE = Homogeneous Collection (If Possible)
    MODE = Geometry - Assemble One Level
    AGGREGATE -> VertexCreator_5
VertexCreator_5
    YVAL = @Value(GL_Y)
    MODE_NAME = Replace with Point
    XVAL = @Value(GL_X)
    INDEX = 0
    -> CRABadrID
CRABadrID: Counter
    SCOPE = Local
    DOMAIN = counter
    CNT_ATTR = CRABadrID
    START = 1
    -> AttributeCreator_5
AttributeCreator_5
    ATTR_TABLE = SET_TO CRABadrID = GL@Value(CRABadrID)
    -> ListExploder
ListExploder
    ATTR_ACCUM_MODE = Merge Incoming List
    LIST_ATTR = _InwListperBevRegadr{}
    ATTR_CONFLICT_RES = Use Incoming List
    ELEMENTS -> AttributeCreator_20
Note: geen match CRAB: (0,0)
VertexCreator
    YVAL = 0
    MODE_NAME = Replace with Point
    XVAL = 0
    INDEX = 0
    -> AttributeCreator_8
AttributeRenamer_6
    ATTR_LIST = _stat_CRAB_merge,CRAB_merge,
    -> StatisticsCalculator_3
StatisticsCalculator_3
    STATS_ATTRS = BevRegID
    COMPUTE_HISTOGRAM = NO
    PREPEND_ATTR_NAME_CHOICE = For multiple results only
    COUNT_ATTR = InwTotal
    COMPLETE -> StatisticsCalculator_4
StatisticsCalculator_4
    GROUP_BY = InwTotal CRAB_merge
    STATS_ATTRS = BevRegID
    COMPUTE_HISTOGRAM = NO
    PREPEND_ATTR_NAME_CHOICE = For multiple results only
    COUNT_ATTR = InwCount
    SUMMARY -> AttributeCreator_21
AttributeCreator_21
    ATTR_LIST = InwPct,@Evaluate(100*@Value(InwCount)/@Value(InwTotal))
    -> 001_Stats_BevRegCRABMatch (writer CSV_1)
001_Stats_BevRegCRABMatch (writer CSV_1)
    attributes: CRAB_merge char(100), InwCount number(10,0), InwPct number(10,6), InwTotal number(10,0)

Bookmark: Merge types BevReg - CRAB
Note: Merged on STRAATNM, HUISNR and SUBADR
AttributeCreator_3
    ATTR_LIST = CRAB_merge,STRAATNM, HUISNR en SUBADR
    -> AttributeCopier_3
Note: Merged on STRAATNM, HUISNR
AttributeCreator_6
    ATTR_LIST = CRAB_merge,STRAATNM, HUISNR
    -> AttributeCopier_3
AttributeCopier_3
    ATTR_LIST = CRAB_merge,_stat_CRAB_merge,
    -> Location_BevReg
Note: No clean data: adres BevReg gecorrigeerd door geolocator
Note: Merged on geolocator STRAATNM and HUISNR
AttributeCreator_7
    ATTR_LIST = CRAB_merge,Geolocator adjusted STRAATNM en HUISNR: @Value(GL_Match)% @Value(GL_Bron),_stat_CRAB_merge,Geolocator adjusted STRAATNM en HUISNR: @Value(GL_Bron)
    -> Location_BevReg
Note: No clean data: adres BevReg niet in GRAB, wel in CRAB geolocator?
Note: Not merged GeoLocator XY
AttributeCreator_20
    ATTR_LIST = CRAB_merge,GeoLocator XY: @Value(GL_Match)% @Value(GL_Bron),_stat_CRAB_merge,GeoLocator XY: @Value(GL_Bron),STRAATNM,@Value(GL_Straatnm),HUISNR,@Value(GL_Huisnr),GEMNM,@Value(GL_Gemnm),PKANCODE,@Value(GL_Postcode)
    -> Location_BevReg
Note: No clean data: adres BevReg niet in GRAB/CRAB
Note: Not Merged
AttributeCreator_8
    ATTR_LIST = CRAB_merge,Data Error: geen CRAB,_stat_CRAB_merge,Data Error: geen CRAB
    -> Location_BevReg
Location_BevReg: TestFilter
    DEFAULT_VALUE = No location
    TEST_LIST = BOOL_OP,OR,COMPOSITE_TEST,<Unused>,TEST_CLAUSE,"TEST @Value(CRAB_merge) NOT_LIKE %geen CRAB%",Location
    Location -> AttributeRenamer_3
    Location -> 001_BevReg_CRAB (writer FFS_3)
    Location -> AttributeRenamer_6
    Location -> GeometryExtractor
    No location -> AttributeRenamer_6

Bookmark: Geocoding via Geolocator Stad Gent (GRAB binnen Gent, CRAB buiten Gent)
Note: Format adres voor request
AttributeCreator_9
    ATTR_TABLE:
      SET_TO Adres = @Value(CRAB_Straatnaam) @TrimLeft(@Value(HUISNR),0), Gent
      SET_TO URL = $(GeolocatorRequestURL)@Value(Adres)
    -> HTTPCaller
HTTPCaller
    TARGET_ATTR = _response_body
    HTTP_METHOD = GET
    STATUS_CODE_ATTR = _http_status_code
    TARGET_ATTR_ENCODING = auto-detect
    VERIFY_SSL_CERTIFICATES = Yes
    SAVE_FILE = Attribute
    RESPONSE_HEADER_LIST_ATTR = _headers
    CONNECTION_TIMEOUT_LENGTH = 60
    ERROR_ATTR = _error
    TRANSFER_TIMEOUT_LENGTH = 90
    FOLLOW_REDIRECTS = Yes
    TARGET_URL = @Value(URL)
    USE_COOKIES = No
    -> JSONValidator
JSONValidator
    JSON_ATTR = _response_body
    ERROR_LIST_ATTR = _json_error
    PASSED -> JSONFlattener
JSONFlattener
    NEW_ATTRIBUTES = DoCallGLResult{0}.Title DoCallGLResult{0}.STREET DoCallGLResult{0}.STREETNO DoCallGLResult{0}.POSTALCODE DoCallGLResult{0}.MUNICIPALITY1 DoCallGLResult{0}.MATCH DoCallGLResult{0}.SOURCE DoCallGLResult{0}.InfoLocation.X DoCallGLResult{0}.InfoLocation.Y
    RECURSIVE = Yes
    JSON_ATTR = _response_body
    -> AttributeRenamer_2
AttributeRenamer_2
    ATTR_LIST = DoCallGLResult{0}.InfoLocation.X,GL_X,,DoCallGLResult{0}.InfoLocation.Y,GL_Y,,DoCallGLResult{0}.Match,GL_Match,,DoCallGLResult{0}.Title,GL_Adres,,DoCallGLResult{0}.Attributes{0}.Value,GL_Straatnm,,DoCallGLResult{0}.Attributes{1}.Value,GL_Huisnr,,DoCallGLResult{0}.Attributes{2}.Value,GL_Postcode,,DoCallGLResult{0}.Attributes{3}.Value,GL_Gemnm,,DoCallGLResult{0}.Attributes{6}.Value,GL_Bron,
    -> AttributeRemover_4
AttributeRemover_4
    REMOVE_ATTRS = _http_status_code,_response_body
    LIST_ATTRS = _headers{} DoCallGLResult{}
    -> Tester_3

Bookmark: OUTPUT: BevReg_adr_notCRAB
GeometryExtractor
    OGC_WKT_PRECISION_DISPLAY = Shortened 64-bit
    ATTR = _geometry
    KIND_LONG = OGC Well Known Text
    REMOVE_GEOMETRY = No
    OGCVERSION = 1.1
    -> Aggregator_2
Aggregator_2
    GROUP_BY = CRABadrID
    ORDERED = No
    SEP = ,
    ACCUM_ATTRS_NAME = Yes
    AGGREGATE_TYPE = Homogeneous Collection (If Possible)
    MODE = Geometry - Assemble One Level
    AGGREGATE -> GeometryReplacer
GeometryReplacer
    OGC_WKT_PRECISION_DISPLAY = 64-bit
    KIND_LONG = OGC Well Known Text
    SOURCE = @Value(_geometry)
    REMOVE_ATTRIBUTE = Yes
    -> TestFilter_3
Note: Extra adressen obv KAD / * KAD adres dat enkel op hoofdadres (STRAAT en HUISNR) met CRAB gematched / >> als afzonderlijk adres beschouwd (verschillend SUBNUMMER) - HFD00000 zodat / * KAD adres dat eerst door geolocator (match>90) en nadien gematched op STRAAT en HUISNR / >> KAD adressen zijn gecorrigeerd. bvb 5A > 5, ...: als afzonderlijk adres beschouwd - COR00000 / *Adres dat na geocoderen niet meer kan gemerged aan CRAB-adres / (No clean data: adres BevReg niet in CRAB, wel in CRAB geolocator? Te onderzoeken) / >> Nieuwe CRAB_adrID aangemaakt (GL0000)
TestFilter_3
    DEFAULT_VALUE = <UNFILTERED>
    TEST_LIST:
      BOOL_OP,OR,COMPOSITE_TEST,<Unused>,TEST_CLAUSE,"TEST @Value(CRABadrID) LIKE GL%
      TEST @Value(CRABadrID) LIKE COR%
      TEST @Value(CRABadrID) LIKE HFD%",extra adr
    extra adr -> AttributeCreator_15
AttributeCreator_15
    ATTR_TABLE = SET_TO adrType = @Substring(@Value(CRABadrID),0,@FindRegEx(@Value(CRABadrID),[0-9]))
    -> AttributeRenamer_4
    -> 001_BevReg_adr_notCRAB (writer FFS_4)
001_BevReg_adr_notCRAB (writer FFS_4)
    attributes: POSTKODE varchar(4), STRAATKODE varchar(8), NUMMER varchar(5), INDEX varchar(5), sector varchar(5), stadsdeel varchar(16), wijknaam varchar(30), CRAB_merge varchar(254), CRABadrID varchar(10), GEMNM varchar(4), HUISNR varchar(10), PKANCODE number(11,0), STRAATNM varchar(255), SUBADRES varchar(255), adrType varchar(4)
AttributeRenamer_4
    ATTR_LIST = NATIONALITEIT,NATIONALIT,,GEZINSGROOTTE,GEZINSGROO,
    -> 001_BevReg_adr_notCRAB (writer SHAPE_1)
001_BevReg_adr_notCRAB (writer SHAPE_1)
    attributes: POSTKODE char(4), STRAATKODE char(8), NUMMER char(5), INDEX char(5), sector char(5), stadsdeel char(16), wijknaam char(30), CRAB_merge char(254), CRABadrID char(10), GEMNM char(4), HUISNR char(10), PKANCODE number(11,0), STRAATNM char(254), SUBADRES char(254), adrType char(4)

Bookmark: OUTPUT: AlleInwoners_CRAB
AttributeRenamer_3
    ATTR_LIST = NATIONALITEIT,NATIONALIT,,GEZINSGROOTTE,GEZINSGROO,
    -> 001_BevReg_CRAB (writer SHAPE_1)
001_BevReg_CRAB (writer SHAPE_1)
    attributes: POSTKODE char(4), STRAATKODE char(8), NUMMER char(5), INDEX char(5), GEBDAT char(11), GESLACHT char(2), NATIONALIT number(4,0), VERWERVING number(3,0), REFPERS char(2), GEZINSGROO number(3,0), AANTKIND number(3,0), BURGSTAAT char(15), NAT_OUD number(4,0), REGISTER char(6), sector char(5), stadsdeel char(16), wijknaam char(30), gemeensch char(12), BevRegID char(10), CRAB_merge char(254), CRABadrID char(10), GEMNM char(4), HUISNR char(10), PKANCODE number(11,0), STRAATNM char(254), SUBADRES char(254)
001_BevReg_CRAB (writer FFS_3)
    attributes: POSTKODE varchar(4), STRAATKODE varchar(8), NUMMER varchar(5), INDEX varchar(5), GEBDAT varchar(11), GESLACHT varchar(2), NATIONALITEIT number(4,0), VERWERVING number(3,0), REFPERS varchar(2), GEZINSGROOTTE number(3,0), AANTKIND number(3,0), BURGSTAAT varchar(15), NAT_OUD number(4,0), REGISTER varchar(6), sector varchar(5), stadsdeel varchar(16), wijknaam varchar(30), gemeensch varchar(12), BevRegID varchar(10), CRAB_merge varchar(254), CRABadrID varchar(10), GEMNM varchar(4), HUISNR varchar(10), PKANCODE number(11,0), STRAATNM varchar(255), SUBADRES varchar(255)
